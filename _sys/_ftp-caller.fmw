FME workspace _ftp-caller.fmw

Parameters:
- RotDirectory = ../   # Katalogen där processen startar
- ProcessName =   # Processnamn
- FtpUrl =   # FTP-URL
- User =   # Användarnamn
- Password =   # Lösenord
- OutputDirectory = ../   # Katalog för lagring av nedladdat
- ProcessModulName =   # Processmodulsnamn
- IsWholeProcessRun = 1   # Är hela datalagerprocessen körd

Writers:
- DATAFILE_1: DATAFILE to $(OutputDirectory)

Note: Parametrar / * [RotDirectory] Kommer från batch-processen och är obligatoriskt för alla FME-processor. / * [ProcessName] Kommer från batch-processen och är obligatoriskt för alla FME-processor. / * [FtpUrl] URL:n, enligt FTP-protokoll, till nedladdningsbar fil (workspace endast anpassad för en fil). / * [User] Användarnamn att logga på med under ovan FTP-adress. / * [Password] Lösenord att logga på med under ovan FTP-adress. / * [OutputDirectory] Katalog där nedladdad fil ska sparas.
Creator
    NUM = 1
    GEOMTYPE = Geometry Object
    CREATED -> UUIDGenerator_2
ParameterFetcher_2
    ATTR_LIST = PathDownload $(FtpUrl) RotDirectory $(RotDirectory) ProcessName $(ProcessName)
    -> AttributeSplitter_3
FTPCaller
    ERROR_ATTR = Exception
    AUTH_TYPE = AUTH_PASSWORD
    TRANSFER_TYPE = Download to an Attribute
    TARGET_ATTR = data_file_data
    FTP_PASSWORD = $(Password)
    REMOTE_URL = $(FtpUrl)
    FTP_USERNAME = $(User)
    MODE = Binary
    VERIFY_SSL_CERTIFICATES = Yes
    CONNECTION_MODE = Passive
    TARGET_ATTR_ENCODING = utf-8
    PROXY_TYPE = FME
    -> Counter
    <REJECTED> -> TimeStamper_2
Counter
    SCOPE = Global
    CNT_ATTR = _id
    DOMAIN = counter
    START = 0
    -> AttributeRemover
    -> FeatureMerger [REQUESTOR]
FeatureMerger
    SUPPLIERS_FIRST = No
    ATTR_CONFLICT_RES = Use Requestor
    REJECT_NULL_MISSING_KEYS = No
    MERGE_TYPE = Attributes Only
    JOIN_KEYS = @Value(_id) @Value(_id) AUTO
    IGNORE_NULLS = No
    ATTR_ACCUM_MODE = Merge Supplier
    PROCESS_DUPS = No
    MERGED -> StringConcatenator_8
    UNMERGED_REQUESTOR -> StringConcatenator_2
    <REJECTED> -> StringConcatenator_2
StringConcatenator_8
    PARM_LINE = @Value(Folder)@Value(FileName)
    VAL_ATTR = PathSave
    ACTION = Create New Attribute
    -> Katalog
Note: Skapar katalog för nedladdad fil
Katalog: WorkspaceRunner
    WORKSPACE_PARAMETERS = FolderPath,@Value(Folder),ProcessName,@Value(ProcessName),ProcessID,@Value(ProcessID),RotDirectory,@Value(RotDirectory),ProcessModulName,$(ProcessModulName),IsWholeProcessRun,$(IsWholeProcessRun)
    WORKSPACE_FILE = $(FME_MF_DIR)_folder-creator.fmw
    BLOCKING = Yes
    SUCCEEDED -> StringConcatenator_3
    SUCCEEDED -> File1 (writer DATAFILE_1)
    FAILED -> StringConcatenator_5
File1 (writer DATAFILE_1)

Bookmark: Skapar universalt unikt spårbarhet
UUIDGenerator_2
    UUID_ATTR = ProcessID
    -> TimeStamper_5
TimeStamper_5
    TIME_ATTR = _timestamp4Unik
    FMT = ^Y^m^dT^H^M^S
    -> StringConcatenator_9
StringConcatenator_9
    PARM_LINE = @Value(_timestamp4Unik)_@Value(ProcessID)
    VAL_ATTR = _tracking_unik_name
    ACTION = Create New Attribute
    -> ParameterFetcher_2

Bookmark: Skapar katalog för nedladdning
AttributeSplitter_3
    LIST_NAME = _FolderName
    DROP_EMPTY_PARTS = No
    ATTR_NAME = ProcessName
    DELIMITER = _
    TRIM_OPTION = Both
    -> ListIndexer_2
ListIndexer_2
    INDEX = 0
    LIST_ATTR = _FolderName{}
    -> StringConcatenator_10
Note: Fullständig sökväg till nedladdningskatalog
StringConcatenator_10
    PARM_LINE = @Value(RotDirectory)@Value(_FolderName)/_ned/
    VAL_ATTR = Folder
    ACTION = Create New Attribute
    -> StringConcatenator

Bookmark: Loggning
StringConcatenator
    PARM_LINE = Fil "@Value(PathDownload)" laddas ner till "@Value(Folder)".
    VAL_ATTR = Logg
    ACTION = Create New Attribute
    -> TimeStamper
TimeStamper
    TIME_ATTR = Timestamp
    FMT = ^Y-^m-^d ^H:^M:^S
    -> Logg_01
    -> FTPCaller
StringConcatenator_5
    PARM_LINE = Katalog @Value(Folder) kunde inte skapas.
    VAL_ATTR = Exception
    ACTION = Create New Attribute
    -> TimeStamper_6
TimeStamper_6
    TIME_ATTR = Timestamp
    FMT = ^Y-^m-^d ^H:^M:^S
    -> Logg_04
Logg_04: WorkspaceRunner
    WORKSPACE_PARAMETERS = EX_DATE_TIME,@Value(Timestamp),EX_PROCESS_NAME,@Value(ProcessName),EX_ID,@Value(ProcessID),EX_TYPE,ERROR,EX,@Value(Exception),EX_WorkSpace,$(FME_MF_DIR_USERTYPED)$(FME_MF_NAME),EX_ROT_DIRECTORY,@Value(RotDirectory),EX_PROCESS_MODUL_NAME,$(ProcessModulName),IsWholeProcessRun,$(IsWholeProcessRun)
    WORKSPACE_FILE = $(FME_MF_DIR)_logg.fmw
    BLOCKING = Yes
StringConcatenator_3
    PARM_LINE = Fil "$(FtpUrl)" nedladdad till "@Value(Folder) med filnamn @Value(FileName)".
    VAL_ATTR = Logg
    ACTION = Create New Attribute
    -> TimeStamper_3
TimeStamper_3
    TIME_ATTR = Timestamp
    FMT = ^Y-^m-^d ^H:^M:^S
    -> Logg_05
Logg_05: WorkspaceRunner
    WORKSPACE_PARAMETERS = EX_DATE_TIME,@Value(Timestamp),EX_PROCESS_NAME,@Value(ProcessName),EX_ID,@Value(ProcessID),EX_TYPE,KLART,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
    WORKSPACE_FILE = $(FME_MF_DIR)_logg.fmw
    BLOCKING = Yes
StringConcatenator_2
    PARM_LINE = Filnamn kunde inte skapas.
    VAL_ATTR = Exception
    ACTION = Create New Attribute
    -> TimeStamper_4
TimeStamper_4
    TIME_ATTR = Timestamp
    FMT = ^Y-^m-^d ^H:^M:^S
    -> Logg_03
Logg_03: WorkspaceRunner
    WORKSPACE_PARAMETERS = EX_DATE_TIME,@Value(Timestamp),EX_PROCESS_NAME,@Value(ProcessName),EX_ID,@Value(ProcessID),EX_TYPE,ERROR,EX,@Value(Exception),EX_WorkSpace,$(FME_MF_DIR_USERTYPED)$(FME_MF_NAME),EX_ROT_DIRECTORY,@Value(RotDirectory),EX_PROCESS_MODUL_NAME,$(ProcessModulName),IsWholeProcessRun,$(IsWholeProcessRun)
    WORKSPACE_FILE = $(FME_MF_DIR)_logg.fmw
    BLOCKING = Yes
TimeStamper_2
    TIME_ATTR = Timestamp
    FMT = ^Y-^m-^d ^H:^M:^S
    -> Logg_02
Logg_02: WorkspaceRunner
    WORKSPACE_PARAMETERS = EX_DATE_TIME,@Value(Timestamp),EX_PROCESS_NAME,@Value(ProcessName),EX_ID,@Value(ProcessID),EX_TYPE,ERROR,EX,@Value(Exception),EX_WorkSpace,$(FME_MF_DIR_USERTYPED)$(FME_MF_NAME),EX_ROT_DIRECTORY,@Value(RotDirectory),EX_PROCESS_MODUL_NAME,$(ProcessModulName),IsWholeProcessRun,$(IsWholeProcessRun)
    WORKSPACE_FILE = $(FME_MF_DIR)_logg.fmw
    BLOCKING = Yes
Logg_01: WorkspaceRunner
    WORKSPACE_PARAMETERS = EX_DATE_TIME,@Value(Timestamp),EX_PROCESS_NAME,@Value(ProcessName),EX_ID,@Value(ProcessID),EX_TYPE,INFORMATION,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
    WORKSPACE_FILE = $(FME_MF_DIR)_logg.fmw
    BLOCKING = No

Bookmark: Filnamn skapas
AttributeRemover
    REMOVE_ATTRS = data_file_data
    -> AttributeSplitter_2
AttributeSplitter_2
    LIST_NAME = _filename
    DROP_EMPTY_PARTS = Yes
    ATTR_NAME = PathDownload
    DELIMITER = \
    TRIM_OPTION = Both
    -> AttributeSplitter
AttributeSplitter
    LIST_NAME = _filename
    DROP_EMPTY_PARTS = Yes
    ATTR_NAME = PathDownload
    DELIMITER = /
    TRIM_OPTION = Both
    -> ListElementCounter
ListElementCounter
    LIST_NAME = _filename{}
    CNT_ATTR = _filename_count
    -> ExpressionEvaluator
ExpressionEvaluator
    VAL_ATTR = _elmnt2FileName
    ACTION = Create New Attribute
    EXPRESSION = @Value(_filename_count)-1
    -> ListIndexer
ListIndexer
    INDEX = @Value(_elmnt2FileName)
    LIST_ATTR = _filename{}
    -> AttributeRemover_2
AttributeRemover_2
    LIST_ATTRS = _filename{} _FolderName{}
    REMOVE_ATTRS = Timestamp,_creation_instance,Logg,_timestamp4Unik,PathDownload,_filename_count,_elmnt2FileName,Folder,RotDirectory,ProcessID,ProcessName
    -> Tester

Bookmark: Om text för filnamn saknas, skapa godtyckligt
Tester
    TEST_CLAUSE:
      TEST _filename ATTRIBUTE_VALUE_NULL ""
      TEST _filename ATTRIBUTE_IS_EMPTY ""
      TEST _filename ATTRIBUTE_IS_MISSING ""
    BOOL_OP = OR
    TEST_MODE = Automatic
    TEST_DESCRIPTION = ""
    PASSED -> StringConcatenator_4
    FAILED -> AttributeCopier
StringConcatenator_4
    PARM_LINE = nedladdad_@Value(_tracking_unik_name)
    VAL_ATTR = FileName
    ACTION = Create New Attribute
    -> FeatureMerger [SUPPLIER]
AttributeCopier
    ATTR_TABLE = COPY _filename > FileName
    -> FeatureMerger [SUPPLIER]
