FME workspace _schema.fmw

Parameters:
- RotDirectory = ../   # Katalogen där processen startar
- ProcessName =   # Processnamn
- DataFormat =   # Input Format
- InData = LKR_GIS   # Indata (shape, zip eller databasschema)
- InData-DatabasTable = NULL
- OutSchemaFileNameSuffix = init   # Suffix på filnamn för schemalistning (skapas med bindestreck)
- OutputDirectory =   # Katalog för lagring av del av datalager
- OutSchemaFileName = schema-$(OutSchemaFileNameSuffix)   # Filnamn för schemalistning
- OutSchemaFileExtention = .xlsx   # Filändelse för schemlistning
- Out = $(OutputDirectory)$(OutSchemaFileName)$(OutSchemaFileExtention)   # Schema-dokumentation

Readers:
- SCHEMA_1: SCHEMA from $(InData)
- ORACLE_SPATIAL_1: ORACLE_SPATIAL from $(InData)

Writers:
- XLSXW_1: XLSXW to $(Out)

Note: Parametrar / * [RotDirectory] Kommer från batch-processen och är obligatoriskt för alla FME-processor. / * [ProcessName] Kommer från batch-processen och är obligatoriskt för alla FME-processor. / * [DataFormat] Styr SchemaReader till vilket format som väntas och hanteras. / * [InData] Fil(er) eller databas (samma benämning behöver vara definierad som databasanslutning) / * [InData-DatabasTable] Om databas skickas in som InData ska tabeller tänkta att användas listas här. Flera tabeller listas med mellanslag. NULL som default-värde för / * [OutputDirectory] Katalogsökväg där schemat skrivs ut till. / Privata / * [OutSchemaFileExtention] Excel-fil 2007 (xlsx). / * [OutSchemaFileName] Filnamn / * [Out] Kompletta sökvägen till fil och den parameter som FME-skrivaren använder. En sammanställning av [OutputDirectory][OutSchemaFileName][OutSchemaFileExtention]
schema (reader SCHEMA_1)
    attributes: fme_feature_type_name varchar(200)
    -> ParameterFetcher
ParameterFetcher
    ATTR_LIST = ProcessName $(ProcessName) RotDirectory $(RotDirectory) InData $(InData) OutputDirectory $(OutputDirectory)
    -> UUIDGenerator_2
UUIDGenerator_2
    UUID_ATTR = ProcessID
    -> ListExploder
    -> ConcatenatedSample [StringAttribute]
ListExploder
    ATTR_ACCUM_MODE = Merge List Attributes
    INDEX_ATTR = _element_index
    ATTR_CONFLICT_RES = Use List Attribute Values
    LIST_ATTR = attribute{}
    ELEMENTS -> AttributeRenamer
    <REJECTED> -> ConcatenatedSample_2 [StringAttribute]
AttributeRenamer
    ATTR_TABLE = RENAME_SET_DEFAULT name > column_name
    -> AttributeCreator
AttributeCreator
    ATTR_TABLE:
      SET_TO dl_need_new_column_name = false
      SET_TO dl_new_column_name
      SET_TO dl_export = true
    -> FilenamePartExtractor
FilenamePartExtractor
    DIRPATH_ATTR = _dirpath
    FULLNAME_ATTR = DatasetFull
    SRC_ATTR = @Value(fme_dataset)
    ROOTNAME_ATTR = Dataset
    EXTENSION_ATTR = _extension
    DIRNAME_ATTR = _dirname
    -> StringLengthCalculator
Note: Beräknar längd kolumnnamn
StringLengthCalculator
    SRC_ATTR = column_name
    LENGTH_ATTR = column_name_char_length
    -> Tester
AttributeCopier
    ATTR_TABLE = COPY column_name > dl_new_column_name = @Value(column_name)
    -> AttributeCreator_2_OUTPUT
AttributeCreator_2_OUTPUT: Junction
    -> FeatureHolder
FeatureHolder
    -> Sampler
    -> schema (writer XLSXW_1)
schema (writer XLSXW_1)
    attributes: fme_feature_type_name string(20), column_name auto(20), dl_need_new_column_name auto(20), dl_new_column_name auto(20), dl_export string(20), fme_data_type auto(20), native_data_type auto(20), fme_format_long_name string(20), fme_format_short_name string(20), _dirpath auto(20), _extension auto(20), DatasetFull auto(20), Dataset auto(20), column_name_char_length auto(20)

Bookmark: Markerar för långa kolumnnamn för Shape
Tester
    TEST_MODE = Automatic
    TEST_DESCRIPTION = ""
    BOOL_OP = AND
    TEST_CLAUSE = TEST @Value(column_name_char_length) > 10
    PASSED -> AttributeCreator_2
    FAILED -> AttributeCopier
AttributeCreator_2
    ATTR_TABLE = SET_TO dl_need_new_column_name = true
    -> AttributeCreator_2_OUTPUT

Bookmark: Loggning
Sampler
    RATE = 1
    SAMPLE_TYPE_LONG = First N Features
    SAMPLE_MODE = No
    SAMPLED -> StringConcatenator_7
StringConcatenator_7
    PARM_LINE = Schema-dokumentation "$(OutSchemaFileName)$(OutSchemaFileExtention)" skapad under "$(OutputDirectory)".
    VAL_ATTR = Logg
    ACTION = Create New Attribute
    -> TimeStamper_6
TimeStamper_6
    TIME_ATTR = Timestamp
    FMT = ^Y-^m-^d ^H:^M:^S
    -> Logg_7
Logg_7: WorkspaceRunner
    WORKSPACE_PARAMETERS = EX_DATE_TIME,@Value(Timestamp),EX_PROCESS_NAME,@Value(ProcessName),EX_ID,@Value(ProcessID),EX_TYPE,KLART,EX,@Value(Logg),EX_WorkSpace,$(FME_MF_DIR_USERTYPED)$(FME_MF_NAME),EX_ROT_DIRECTORY,@Value(RotDirectory)
    BLOCKING = No
    WORKSPACE_FILE = $(FME_MF_DIR)_logg.fmw
ConcatenatedSample_2
    NumberToShorten = 3
    FME_DATASET = @Value(fme_dataset)
    StringConcatenatedSample -> StringConcatenator_3
StringConcatenator_3
    PARM_LINE = Följande, @Value(fme_dataset_concatenated), dataset kunde inte kolumninformation utläsas ifrån (totalt @Value(TotaltAntal) st.).
    VAL_ATTR = Logg
    ACTION = Create New Attribute
    -> TimeStamper_3
TimeStamper_3
    TIME_ATTR = Timestamp
    FMT = ^Y-^m-^d ^H:^M:^S
    -> Logg_3
Logg_3: WorkspaceRunner
    WORKSPACE_PARAMETERS = EX_DATE_TIME,@Value(Timestamp),EX_PROCESS_NAME,@Value(ProcessName),EX_ID,@Value(ProcessID),EX_TYPE,VARNING,EX,@Value(Logg),EX_WorkSpace,$(FME_MF_DIR_USERTYPED)$(FME_MF_NAME),EX_ROT_DIRECTORY,@Value(RotDirectory)
    BLOCKING = No
    WORKSPACE_FILE = $(FME_MF_DIR)_logg.fmw
ConcatenatedSample
    NumberToShorten = 3
    FME_DATASET = @Value(fme_dataset)
    StringConcatenatedSample -> StringConcatenator_2
StringConcatenator_2
    PARM_LINE = Kartlägger schemastruktur för dataseten @Value(fme_dataset_concatenated) (totalt @Value(TotaltAntal) st.) efter inparametern "@Value(InData)".
    VAL_ATTR = Logg
    ACTION = Create New Attribute
    -> TimeStamper_2
TimeStamper_2
    TIME_ATTR = Timestamp
    FMT = ^Y-^m-^d ^H:^M:^S
    -> Logg_2
Logg_2: WorkspaceRunner
    WORKSPACE_PARAMETERS = EX_DATE_TIME,@Value(Timestamp),EX_PROCESS_NAME,@Value(ProcessName),EX_ID,@Value(ProcessID),EX_TYPE,INFORMATION,EX,@Value(Logg),EX_WorkSpace,$(FME_MF_DIR_USERTYPED)$(FME_MF_NAME),EX_ROT_DIRECTORY,@Value(RotDirectory)
    BLOCKING = No
    WORKSPACE_FILE = $(FME_MF_DIR)_logg.fmw

FME custom transformer ConcatenatedSample

Parameters:
- FME_DATASET = @Value(fme_dataset)   # Attribute to Sample Concatenate
- NumberToShorten = 3   # Antal innan förkortning

StringAttribute (input)
    -> Aggregator
Aggregator
    ORDERED = No
    MODE = Geometry - Assemble One Level
    LIST_ATTRS_TO_INCLUDE = fme_dataset
    SEP = ,
    COUNT_ATTR = TotaltAntal
    LIST_NAME = dataset
    GROUP_BY = fme_dataset
    AGGREGATE_TYPE = Homogeneous Collection (If Possible)
    ACCUM_ATTRS_NAME = Use Attributes From One Feature
    AGGREGATE -> Tester_2
Tester_2
    TEST_MODE = Automatic
    TEST_DESCRIPTION = ""
    BOOL_OP = OR
    TEST_CLAUSE = TEST @Value(TotaltAntal) < 3
    PASSED -> ListIndexer
    FAILED -> ListConcatenator
ListIndexer
    PREFIX = _ds0_
    INDEX = 0
    LIST_ATTR = dataset{}
    -> ListIndexer_2
ListIndexer_2
    PREFIX = _ds1_
    INDEX = 1
    LIST_ATTR = dataset{}
    -> ListIndexer_3
ListIndexer_3
    PREFIX = _dsn_
    INDEX = @Value(TotaltAntal)-1
    LIST_ATTR = dataset{}
    -> StringConcatenator
StringConcatenator
    PARM_LINE = @Value(_ds0_fme_dataset), @Value(_ds1_fme_dataset), ... , @Value(_dsn_fme_dataset)
    VAL_ATTR = fme_dataset_concatenated
    ACTION = Create New Attribute
    -> StringConcatenator_OUTPUT_-__StringConcatenator_Output
ListConcatenator
    SEP = ", "
    VAL_ATTR = fme_dataset_concatenated
    DROP_EMPTY_PARTS = No
    LIST_ATTR = dataset{}.fme_dataset
    -> StringConcatenator_OUTPUT_-__StringConcatenator_Output
StringConcatenator_OUTPUT_-__StringConcatenator_Output: Junction
    -> AttributeRemover
AttributeRemover
    LIST_ATTRS = dataset{} dataset{}.fme_dataset
    REMOVE_ATTRS = fme_dataset,_ds1_fme_dataset,_dsn_fme_dataset,dataset{0}.fme_dataset,_ds0_fme_dataset
    -> StringConcatenatedSample (output)
StringConcatenatedSample (output)
