FME workspace modul-settings-datasets_checks.fmw

Parameters:
- ROOT_PATH = C:\dev\Datalager_procsrc   # Rotsökväg processinstans

Creator
    GEOMTYPE = Geometry Object
    NUM = 1
    CREATED -> FeatureReader_2 [INITIATOR]
FeatureReader_2
    ATTRIBUTES = PATH,"path_unix,path_windows,path_rootname,path_filename,path_extension,path_directory_unix,path_directory_windows,path_type,fme_geometry{0}"
    ATTR_ACCUM_MODE = Only Use Result
    COMBINE_GEOM = Use Result
    DATASET = $(ROOT_PATH)
    FORMAT = PATH
    OUTPUT_FEATURES_DISPLAY = Schema and Data Features
    PATH_GLOB_PATTERN = *_schema\_modul-settings-datasets.ini
    PATH_NO_EMPTY_PROPERTIES = YES
    PATH_OFFSET_DATETIME = yes
    PATH_RECURSE_DIRECTORIES = YES
    PATH_RETRIEVE_FILE_PROPERTIES = NO
    PATH_TYPE = FILE
    PATH_USE_NON_STRING_ATTR = yes
    PATH -> Tester
Tester
    BOOL_OP = AND
    TEST_CLAUSE:
      CASE_INSENSITIVE_TEST @Value(path_directory_windows) NOT_CONTAINS _bkp
      CASE_INSENSITIVE_TEST @Value(path_directory_windows) NOT_CONTAINS _doc
      CASE_INSENSITIVE_TEST @Value(path_directory_windows) NOT_CONTAINS _deploy
    TEST_MODE = CASE_INSENSITIVE_TEST
    PASSED -> FeatureReader_3 [INITIATOR]
FeatureReader_3
    ATTRS_TO_EXPOSE = col0 col1 col2 col3 col4
    ATTR_ACCUM_MODE = Merge Initiator and Result
    ATTR_CONFLICT_RES = Use Result
    ATTR_IGNORE_NULLS = No
    COMBINE_GEOM = Use Result
    CSV2_CASE_SENSITIVE_FIELD_NAMES = Yes
    CSV2_CHUNK_SIZE = 100000
    CSV2_DATA_START_LINE = 1
    CSV2_DELIMITER = |
    CSV2_ENCODING = windows-1252
    CSV2_ENFORCE_STRICT_SCHEMA = No
    CSV2_FEATURE_TYPE_NAME = FORMAT_NAME
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 1000
    CSV2_SCAN_TYPES = No
    CSV2_SKIP_DUPLICATE_DELIMITERS = No
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = NO
    DATASET = @Value(path_windows)
    FORMAT = CSV2
    INTERACT = NONE
    OUTPUT_FEATURES_DISPLAY = Schema and Data Features
    <OTHER> -> Tester_16
Note: Plockar bort kommentarer och tomma rader
Tester_16
    BOOL_OP = COMPOSITE
    COMPOSITE_TEST = "1 OR ((2 OR 3) AND (4 OR 5 OR 6) AND (7 OR 8 OR 9) AND (10 OR 11 OR 12) AND (13 OR 14 OR 15))"
    TEST_CLAUSE:
      TEST @Value(col0) BEGINS_WITH ;
      TEST col0 ATTRIBUTE_VALUE_NULL ""
      TEST col0 ATTRIBUTE_IS_EMPTY ""
      TEST col1 ATTRIBUTE_VALUE_NULL ""
      TEST col1 ATTRIBUTE_IS_EMPTY ""
      TEST col1 ATTRIBUTE_IS_MISSING ""
      TEST col2 ATTRIBUTE_VALUE_NULL ""
      TEST col2 ATTRIBUTE_IS_EMPTY ""
      TEST col2 ATTRIBUTE_IS_MISSING ""
      TEST col3 ATTRIBUTE_VALUE_NULL ""
      TEST col3 ATTRIBUTE_IS_EMPTY ""
      TEST col3 ATTRIBUTE_IS_MISSING ""
      TEST col4 ATTRIBUTE_VALUE_NULL ""
      TEST col4 ATTRIBUTE_IS_EMPTY ""
      TEST col4 ATTRIBUTE_IS_MISSING ""
    TEST_MODE = TEST
    FAILED -> AttributeCopier
    FAILED -> AttributeKeeper
Datasources: Inspector
AttributeCopier
    ATTR_TABLE = COPY col0 > col0_gemener
    MISSING_INPUT_ATTRS = REMOVE
    -> StringCaseChanger
StringCaseChanger
    ATTRCHOICE = Selected Attributes
    ATTRLIST = col0_gemener
    CHANGE_TYPE = lowercase
    -> Tester_2
Tester_2
    BOOL_OP = OR
    TEST_CLAUSE:
      CASE_INSENSITIVE_TEST @Value(col0_gemener) CONTAINS å
      CASE_INSENSITIVE_TEST @Value(col0_gemener) CONTAINS ä
      CASE_INSENSITIVE_TEST @Value(col0_gemener) CONTAINS ö
    TEST_MODE = PER_TEST
    PASSED -> Datasources_w_åäö
Datasources_w_åäö: Inspector

Bookmark: Processmodulsnamn
AttributeKeeper
    CREATE_BULK_MODE_FEATURES = NO
    KEEP_ATTRS = path_directory_windows,col0,col1,col2,col3,col4
    -> ParameterFetcher
ParameterFetcher
    ATTR_LIST = _ROOT_PATH $(ROOT_PATH)
    -> StringReplacer
StringReplacer
    CASE = NO
    FIND_TEXT = \\
    NO_MATCH = _FME_NO_OP_
    REGEXP = NO
    REPLACE_TEXT = \
    SRC_ATTRS = _ROOT_PATH
    -> ExpressionEvaluator
ExpressionEvaluator
    ACTION = Create New Attribute
    EXPRESSION = @StringLength(@Value(_ROOT_PATH))
    VAL_ATTR = _startIdx
    -> Tester_3
Tester_3
    BOOL_OP = OR
    TEST_CLAUSE = CASE_INSENSITIVE_TEST @Value(_ROOT_PATH) ENDS_WITH \
    TEST_MODE = CASE_INSENSITIVE_TEST
    PASSED -> SubstringExtractor
    FAILED -> ExpressionEvaluator_2
ExpressionEvaluator_2
    ACTION = Overwrite Existing Attributes
    ATTRLIST = _startIdx
    EXPRESSION = @Value(_startIdx)+1
    -> SubstringExtractor
SubstringExtractor
    END = @StringLength(@Value(path_directory_windows))
    RESULT_ATTR = ProcessModuleName
    SRC_STRING = @Value(path_directory_windows)
    START = @Value(_startIdx)
    -> StringSearcher
StringSearcher
    CASE = no
    MATCHED_RESULT_ATTR = _first_match
    MATCHES_ATTR = matches_
    REGEXP = \\
    STRING_TO_SEARCH = @Value(ProcessModuleName)
    MATCHED -> SubstringExtractor_2
    NOT_MATCHED -> Junction
SubstringExtractor_2
    END = @Value(matches_{0}.startIndex)-1
    RESULT_ATTR = ProcessModuleName
    SRC_STRING = @Value(ProcessModuleName)
    START = 0
    -> Junction
Junction
    -> AttributeRemover
AttributeRemover
    LIST_ATTRS = matches_{}
    REMOVE_ATTRS = _ROOT_PATH,_startIdx,_first_match
    -> Datasources
