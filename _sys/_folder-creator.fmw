FME workspace _folder-creator.fmw

Parameters:
- FolderPath =   # Sökväg katalog
- ProcessName =   # Processnamn
- ProcessID =   # Process-ID
- RotDirectory = ../   # Katalogen där processen startar
- ProcessModulName =   # Processmodulsnamn
- IsWholeProcessRun = 1   # Är hela datalagerprocessen körd

Writers:
- FILECOPY_1: FILECOPY to $(FolderPath)

Creator
    GEOMTYPE = Geometry Object
    NUM = 1
    CREATED -> filecopy (writer FILECOPY_1)
    CREATED -> StringConcatenator
filecopy (writer FILECOPY_1)
    attributes: filecopy_source_dataset char(512), filecopy_dest_dataset char(512), filecopy_dest_filename char(128)

Bookmark: Loggning
StringConcatenator
    ACTION = Create New Attribute
    PARM_LINE = Skapar katalog $(FolderPath)
    VAL_ATTR = Logg
    -> DTStamperYYYY-MM-DD_HH:MI:SS.sss
DTStamperYYYY-MM-DD_HH:MI:SS.sss
    -> WorkspaceRunner
WorkspaceRunner
    WORKSPACE_PARAMETERS = EX_DATE_TIME,@Value(_datetimestamp),EX_PROCESS_NAME,$(ProcessName),EX_ID,$(ProcessID),EX_TYPE,INFORMATION,EX,@Value(Logg),EX_WorkSpace,$(FME_MF_DIR_USERTYPED)$(FME_MF_NAME),EX_ROT_DIRECTORY,$(RotDirectory),EX_PROCESS_MODUL_NAME,$(ProcessModulName),IsWholeProcessRun,$(IsWholeProcessRun)
    BLOCKING = No
    WORKSPACE_FILE = $(FME_MF_DIR)_logg.fmw

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    TIMEZONE = local
    INCLUDE_OFFSET = NO
    DATETIME_ATTR = _dts
    STAMP_TYPE = datetime
    -> DateTimeConverter
DateTimeConverter
    REPAIR_INPUT = NO
    DATETIME_ATTR = _dts
    OUT_FORMAT = %Y-%m-%d %H:%M:%S
    -> AttributeCreator
    <REJECTED> -> <Rejected> (output)
AttributeCreator
    ATTR_TABLE = SET_TO _mils = @Value(_dts)
    -> StringReplacer
StringReplacer
    REGEXP = YES
    FIND_TEXT = \.\d*
    NO_MATCH = _FME_NO_OP_
    CASE = NO
    SRC_ATTRS = _dts
    -> StringReplacer_2
StringReplacer_2
    REGEXP = YES
    FIND_TEXT = .*\.
    NO_MATCH = _FME_NO_OP_
    CASE = NO
    SRC_ATTRS = _mils
    -> SubstringExtractor
SubstringExtractor
    START = 0
    RESULT_ATTR = _subMils
    SRC_STRING = @Value(_mils)
    END = 2
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)
