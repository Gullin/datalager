FME workspace _logg.fmw

Parameters:
- EX_DATE_TIME =   # "{}" Exception date time
- EX_PROCESS_NAME =   # Processnamn
- EX_ID =   # Process ID
- EX_TYPE =   # Exception type
- EX =   # " " Exception message
- EX_WorkSpace = $(FME_MF_DIR_USERTYPED)$(FME_MF_NAME)   # Workspace med sökväg
- EX_ROT_DIRECTORY = ../   # Katalogen där processen startar
- EX_PROCESS_MODUL_NAME =   # Processmodulsnamn
- IsWholeProcessRun = 1   # Är hela datalagerprocessen körd
- Destination_exc_file = $(EX_ROT_DIRECTORY)_log/FATAL_ERROR.log   # Sökväg exceptionfil
- Destination_exc_file_local = $(EX_ROT_DIRECTORY)$(EX_PROCESS_MODUL_NAME)/_log/FATAL_ERROR.log   # Sökväg exceptionfil
- Destination_log_file_sqlite = $(EX_ROT_DIRECTORY)_log/DatalagerLogg.sqlite   # Sökväg loggfil

Writers:
- TEXTLINE_1: TEXTLINE to $(Destination_exc_file)
- TEXTLINE_2: TEXTLINE to $(Destination_exc_file_local)
- SQLITE3_1: SQLITE3 to $(Destination_log_file_sqlite)

Note: Sökvägar / Ska workspace köras för sig och inte kallas på genom WorkspaceRunner behöver sökvägarna börja med . (en punkt). Standard och vid körande från WorkspaceRunner ska sökvägarna börja med .. (två punkter). / Gäller för: / * Private Parameters / Destination_exc_file / * Private Parameters / Destination_log_file / * Workspace Parameters / Logging / Log File
Creator
    GEOMTYPE = Geometry Object
    NUM = 1
    CREATED -> AttributeCreator
AttributeCreator
    ATTR_TABLE = SET_TO Exception = $(EX)
    -> ParameterFetcher
ParameterFetcher
    ATTR_LIST = _EX_DATE_TIME $(EX_DATE_TIME) _EX_PROCESS_NAME $(EX_PROCESS_NAME) _EX_ID $(EX_ID) _EX_TYPE $(EX_TYPE) _EX_WorkSpace $(EX_WorkSpace) _IsWholeProcessRun $(IsWholeProcessRun)
    -> Tester_6

Bookmark: Process-ID för spårning
Tester_6
    BOOL_OP = OR
    TEST_CLAUSE:
      TEST _EX_ID ATTRIBUTE_VALUE_NULL ""
      TEST _EX_ID ATTRIBUTE_IS_EMPTY ""
      TEST _EX_ID ATTRIBUTE_IS_MISSING ""
    TEST_MODE = TEST
    PASSED -> AttributeCreator_3
    FAILED -> Tester
AttributeCreator_3
    ATTR_TABLE = SET_TO _EX_ID = EJ SATT I FME-PROCESS
    -> Tester

Bookmark: Datum för loggning, om inte parametern ex_date_time har värde skpas ett värde
Tester
    BOOL_OP = OR
    TEST_CLAUSE:
      TEST _EX_DATE_TIME ATTRIBUTE_VALUE_NULL ""
      TEST _EX_DATE_TIME ATTRIBUTE_IS_EMPTY ""
      TEST _EX_DATE_TIME ATTRIBUTE_IS_MISSING ""
    TEST_MODE = TEST
    PASSED -> DTStamperYYYY-MM-DD_HH:MI:SS.sss
    FAILED -> Tester_4
DTStamperYYYY-MM-DD_HH:MI:SS.sss
    -> AttributeCreator_4
AttributeCreator_4
    ATTR_TABLE = SET_TO _EX_DATE_TIME = @Value(_datetimestamp)
    -> Tester_4

Bookmark: FME Workspace namn
Tester_4
    BOOL_OP = OR
    TEST_CLAUSE:
      TEST _EX_WorkSpace ATTRIBUTE_VALUE_NULL ""
      TEST _EX_WorkSpace ATTRIBUTE_IS_EMPTY ""
      TEST _EX_WorkSpace ATTRIBUTE_IS_MISSING ""
    TEST_MODE = TEST
    PASSED -> StringConcatenator_2
    FAILED -> StringReplacer
StringConcatenator_2
    ACTION = Create New Attribute
    PARM_LINE = $(FME_MF_DIR_USERTYPED)\$(FME_MF_NAME)
    VAL_ATTR = _EX_WorkSpace
    -> StringReplacer
StringReplacer
    CASE = NO
    FIND_TEXT = /
    NO_MATCH = _FME_NO_OP_
    REGEXP = NO
    REPLACE_TEXT = \
    SRC_ATTRS = _EX_WorkSpace
    -> Tester_2

Bookmark: Loggningstyp, informtion, fel etc.
Tester_2
    BOOL_OP = OR
    TEST_CLAUSE:
      TEST _EX_TYPE ATTRIBUTE_VALUE_NULL ""
      TEST _EX_TYPE ATTRIBUTE_IS_EMPTY ""
      TEST _EX_TYPE ATTRIBUTE_IS_MISSING ""
    TEST_MODE = TEST
    PASSED -> AttributeCreator_2
    FAILED -> Tester_3
    FAILED -> AttributeEncoder
AttributeCreator_2
    ATTR_TABLE = SET_TO _EX_TYPE = OKÄND
    -> Tester_3
    -> AttributeEncoder

Bookmark: Endast för fel
Tester_3
    BOOL_OP = OR
    TEST_CLAUSE = TEST @Value(_EX_TYPE) = ERROR
    TEST_MODE = TEST
    PASSED -> StringConcatenator
StringConcatenator
    ACTION = Create New Attribute
    PARM_LINE = @Value(_EX_DATE_TIME) | @Value(_EX_PROCESS_NAME) | @Value(_EX_ID) | @Value(_EX_TYPE) | @Value(Exception) | @Value(_EX_WorkSpace)
    VAL_ATTR = text_line_data
    -> AttributeEncoder_2
AttributeEncoder_2
    ATTRCHOICE = All Attributes
    DEST_ENCODING = windows-1252
    TREAT_AS_BYTES = Honor Encoding
    -> Tester_5
Tester_5
    BOOL_OP = OR
    TEST_CLAUSE = TEST @Value(_IsWholeProcessRun) = 0
    TEST_MODE = TEST
    PASSED -> text_line (writer TEXTLINE_2)
    FAILED -> text_line (writer TEXTLINE_1)
text_line (writer TEXTLINE_2)
    attributes: text_line_data buffer
text_line (writer TEXTLINE_1)
    attributes: text_line_data buffer

Bookmark: Loggning
AttributeEncoder
    ATTRCHOICE = All Attributes
    DEST_ENCODING = windows-1252
    TREAT_AS_BYTES = Honor Encoding
    -> AttributeManager
AttributeManager
    ATTR_TABLE:
      RENAME_SET_VALUE _EX_DATE_TIME > Tidpunkt
      RENAME_SET_VALUE _EX_PROCESS_NAME > Processnamn
      RENAME_SET_VALUE _EX_ID > Process ID
      RENAME_SET_VALUE _EX_TYPE > Typ
      RENAME_SET_VALUE Exception > Meddelande
      RENAME_SET_VALUE _EX_WorkSpace > FME workspace
      REMOVE _creation_instance
      REMOVE _IsWholeProcessRun
      REMOVE _datetimestamp
    -> Generell (writer SQLITE3_1)
Generell (writer SQLITE3_1)
    attributes: Tidpunkt varchar(200), Processnamn varchar(200), Process ID varchar(200), Typ varchar(200), Meddelande varchar(200), FME workspace varchar(200)

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    INCLUDE_OFFSET = NO
    STAMP_TYPE = datetime
    TIMEZONE = local
    -> DateTimeConverter
DateTimeConverter
    DATETIME_ATTR = _dts
    OUT_FORMAT = %Y-%m-%d %H:%M:%S
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    NO_MATCH = _FME_NO_OP_
    REGEXP = YES
    SRC_ATTRS = _dts
    -> StringReplacer_2
StringReplacer_2
    CASE = NO
    FIND_TEXT = .*\.
    NO_MATCH = _FME_NO_OP_
    REGEXP = YES
    SRC_ATTRS = _mils
    -> SubstringExtractor
SubstringExtractor
    END = 2
    RESULT_ATTR = _subMils
    SRC_STRING = @Value(_mils)
    START = 0
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)
