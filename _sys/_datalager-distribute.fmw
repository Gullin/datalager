FME workspace _datalager-distribute.fmw

Parameters:
- RotDirectory = ../   # Katalogen där processen startar
- ProcessName =   # Processnamn
- ProcessModulName =   # Processmodulsnamn
- InData = C:\Dev\Datalager_procsrc\_log/DatalagerDistributionSource.log   # Fil med hänvisning till källkataloger
- RepoSourceDirectory = C:\Dev\Datalager_procsrc\_geodatarepo   # Rotkatalog repositoryt
- IsWholeProcessRun = 1   # Är hela datalagerprocessen körd
- TargetDirectories = $(RotDirectory)\_global-settings-targetpaths.ini   # Målkataloger för datalager

Readers:
- TEXTLINE_1: TEXTLINE from $(InData)
- TEXTLINE_2: TEXTLINE from $(TargetDirectories)

Writers:
- FILECOPY_1: FILECOPY to $(RotDirectory)

Note: Parametrar / * [RotDirectory] Kommer från batch-processen och är obligatoriskt för alla FME-processor. / * [ProcessName] Kommer från batch-processen och är obligatoriskt för alla FME-processor. / * [InData] Textfil med sökvägar till de olika källorna i repositoryt. / * [SourceRepoDirectory] Sökväg till repositorys rotkatalog. Där all data läggs innan distribuering. / Privata / * [TargetDirectories] Målkataloger som datalagret kopieras till.
Note: Källa datalager
text_line (reader TEXTLINE_1)
    attributes: text_line_data buffer
    -> ParameterFetcher_2
ParameterFetcher_2
    ATTR_LIST = _RepoSourceDirectory $(RepoSourceDirectory) ProcessName $(ProcessName) RotDirectory $(RotDirectory) _IsWholeProcessRun $(IsWholeProcessRun) ProcessModulName $(ProcessModulName)
    -> UUIDGenerator_3
UUIDGenerator_3
    UUID_ATTR = ProcessID
    -> AttributeRenamer
    -> Aggregator
AttributeRenamer
    ATTR_TABLE = RENAME_SET_DEFAULT text_line_data > _SourceDirectories
    -> AttributeTrimmer
AttributeTrimmer
    SRC_ATTRS = _RepoSourceDirectory,_SourceDirectories
    TRIM_TYPE = Both
    TRIM_CHARS = " "
    TRIM_TO_NONE = Yes
    -> PathFolderSplitterCleaner [Källa]
PathFolderSplitterCleaner
    _REPOSOURCEDIRECTORY = @Value(_RepoSourceDirectory)
    _SOURCEDIRECTORIES = @Value(_SourceDirectories)
    CleanPath -> AttributeCreator_5
    <Rejected> -> StringConcatenator_5
AttributeCreator_5
    ATTR_TABLE = SET_TO CleanPath_Source = @Value(CleanPath)
    -> AttributeRemover_2
AttributeRemover_2
    REMOVE_ATTRS = CleanPath
    -> AttributeCreator_2
Note: Målkataloger datalager
text_line (reader TEXTLINE_2)
    attributes: text_line_data buffer
    -> Tester_2
Note: Kontrollerar så målkataloger finns, plockar / bort kommentarer och tomma rader
Tester_2
    TEST_DESCRIPTION = ""
    TEST_MODE = Automatic
    BOOL_OP = OR
    TEST_CLAUSE:
      TEST @Value(text_line_data) BEGINS_WITH ;
      TEST text_line_data ATTRIBUTE_VALUE_NULL ""
      TEST text_line_data ATTRIBUTE_IS_EMPTY ""
    FAILED -> AttributeRenamer_2
    FAILED -> Aggregator_2
AttributeRenamer_2
    ATTR_TABLE = RENAME_SET_DEFAULT text_line_data > _TargetDirectories
    -> ListBuilder
Note: Skapar lista för att koppla alla målkataloger till alla / källkataloger genom att senare explodera listan efter merge.
ListBuilder
    LIST_NAME = _targetDirectories
    LIST_ATTRS_TO_INCLUDE = _TargetDirectories
    -> AttributeCreator
FeatureMerger_2
    MERGE_TYPE = Attributes Only
    PROCESS_DUPS = No
    ATTR_ACCUM_MODE = Merge Supplier
    SUPPLIERS_FIRST = No
    IGNORE_NULLS = No
    ATTR_CONFLICT_RES = Use Requestor
    REJECT_NULL_MISSING_KEYS = No
    JOIN_KEYS = @Value(_id) @Value(_id) AUTO
    MERGED -> CleansSubTargetDirectories [DistributionInfo]
    UNMERGED_REQUESTOR -> ListExploder_2
    UNUSED_SUPPLIER -> ListExploder_2
    <REJECTED> -> ListExploder_2
CleansSubTargetDirectories
    _SOURCEDIRECTORIES = @Value(_SourceDirectories)
    -> ListExploder
    <Rejected> -> StringConcatenator_7
ListExploder
    ATTR_CONFLICT_RES = Use List Attribute Values
    INDEX_ATTR = _element_index
    ATTR_ACCUM_MODE = Merge List Attributes
    LIST_ATTR = _targetDirectories{}
    ELEMENTS -> StringConcatenator
    <REJECTED> -> StringConcatenator_6
StringConcatenator
    PARM_LINE = @Value(_TargetDirectories)\@Value(_TargetSubDirectories)
    VAL_ATTR = _Target
    ACTION = Create New Attribute
    -> AttributeRenamer_3
AttributeRenamer_3
    ATTR_TABLE:
      RENAME_SET_DEFAULT CleanPath_Source > filecopy_source_dataset
      RENAME_SET_DEFAULT _Target > filecopy_dest_dataset
    -> AttributeTrimmer_2
AttributeTrimmer_2
    SRC_ATTRS = filecopy_source_dataset,filecopy_dest_dataset
    TRIM_TYPE = Both
    TRIM_CHARS = " "
    TRIM_TO_NONE = Yes
    -> filecopy (writer FILECOPY_1)
    -> Aggregator_5
filecopy (writer FILECOPY_1)
    attributes: filecopy_source_dataset char(512), filecopy_dest_dataset char(512), filecopy_dest_filename char(128)

Bookmark: Endast för att merga
AttributeCreator_2
    ATTR_TABLE = SET_TO _id = 1
    -> FeatureMerger_2 [REQUESTOR]
AttributeCreator
    ATTR_TABLE = SET_TO _id = 1
    -> FeatureMerger_2 [SUPPLIER]

Bookmark: Loggning
StringConcatenator_5
    PARM_LINE = Total sökväg till respektive moduls repository kan ej göras fullt ut. Sammanställningen av rotkatalog och modulkataloger med rätt skiljetecken kan ej göras.
    VAL_ATTR = Exception
    ACTION = Create New Attribute
    -> DTStamperYYYY-MM-DD_HH:MI:SS.sss_4
DTStamperYYYY-MM-DD_HH:MI:SS.sss_4
    -> Logg_04
Logg_04: WorkspaceRunner
    BLOCKING = Yes
    WORKSPACE_FILE = $(FME_MF_DIR)_logg.fmw
    WORKSPACE_PARAMETERS = EX_DATE_TIME,@Value(_datetimestamp),EX_PROCESS_NAME,$(ProcessName),EX_ID,@Value(ProcessID),EX_TYPE,ERROR,EX,@Value(Exception),EX_WorkSpace,$(FME_MF_DIR_USERTYPED)$(FME_MF_NAME),EX_ROT_DIRECTORY,@Value(RotDirectory),EX_PROCESS_MODUL_NAME,@Value(ProcessModulName),IsWholeProcessRun,$(IsWholeProcessRun)
Aggregator
    MODE = Geometry - Assemble One Level
    ORDERED = No
    CONCAT_ATTRS = text_line_data
    COUNT_ATTR = Antal_source
    AGGREGATE_TYPE = Homogeneous Collection (If Possible)
    ACCUM_ATTRS_NAME = Use Attributes From One Feature
    SEP = ", "
    AGGREGATE -> AttributeCreator_3
AttributeCreator_3
    ATTR_TABLE = SET_TO _id = 1
    -> BulkAttributeRenamer
BulkAttributeRenamer
    PATTERN_ACTION_DISP = ADDPREFIX
    MODE_CHOICE = RENAME
    REPLACE_STR = Source_
    ATTRCHOICE = All Attributes
    -> FeatureMerger [REQUESTOR]
Aggregator_5
    MODE = Geometry - Assemble One Level
    ORDERED = No
    CONCAT_ATTRS = filecopy_dest_dataset
    AGGREGATE_TYPE = Homogeneous Collection (If Possible)
    ACCUM_ATTRS_NAME = Use Attributes From One Feature
    SEP = ", "
    AGGREGATE -> StringConcatenator_4
StringConcatenator_4
    PARM_LINE = Distribuering av data från processmodul @Value(ProcessModulName) till @Value(filecopy_dest_dataset) genomfört.
    VAL_ATTR = Logg
    ACTION = Create New Attribute
    -> DTStamperYYYY-MM-DD_HH:MI:SS.sss_8
DTStamperYYYY-MM-DD_HH:MI:SS.sss_8
    -> Logg_3
Logg_3: WorkspaceRunner
    BLOCKING = Yes
    WORKSPACE_FILE = $(FME_MF_DIR)_logg.fmw
    WORKSPACE_PARAMETERS = EX_DATE_TIME,@Value(_datetimestamp),EX_PROCESS_NAME,$(ProcessName),EX_ID,@Value(ProcessID),EX_TYPE,KLART,EX,@Value(Logg),EX_WorkSpace,$(FME_MF_DIR_USERTYPED)$(FME_MF_NAME),EX_ROT_DIRECTORY,@Value(RotDirectory),EX_PROCESS_MODUL_NAME,@Value(ProcessModulName),IsWholeProcessRun,$(IsWholeProcessRun)
StringConcatenator_6
    PARM_LINE = Explodering av lista med målplatser var ej genomförtbart. Felkod: @Value(fme_rejection_code)
    VAL_ATTR = Logg
    ACTION = Create New Attribute
    -> DTStamperYYYY-MM-DD_HH:MI:SS.sss_7
DTStamperYYYY-MM-DD_HH:MI:SS.sss_7
    -> Logg_4
Logg_4: WorkspaceRunner
    BLOCKING = Yes
    WORKSPACE_FILE = $(FME_MF_DIR)_logg.fmw
    WORKSPACE_PARAMETERS = EX_DATE_TIME,@Value(_datetimestamp),EX_PROCESS_NAME,$(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,@Value(ProcessModulName),IsWholeProcessRun,$(IsWholeProcessRun)
StringConcatenator_7
    PARM_LINE = Underkataloger för målrepot kunde ej skapas korrekt. Felkod: @Value(fme_rejection_code)
    VAL_ATTR = Logg
    ACTION = Create New Attribute
    -> DTStamperYYYY-MM-DD_HH:MI:SS.sss_6
DTStamperYYYY-MM-DD_HH:MI:SS.sss_6
    -> Logg_5
Logg_5: WorkspaceRunner
    BLOCKING = Yes
    WORKSPACE_FILE = $(FME_MF_DIR)_logg.fmw
    WORKSPACE_PARAMETERS = EX_DATE_TIME,@Value(_datetimestamp),EX_PROCESS_NAME,$(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,@Value(ProcessModulName),IsWholeProcessRun,$(IsWholeProcessRun)
ListExploder_2
    ATTR_CONFLICT_RES = Use List Attribute Values
    INDEX_ATTR = _element_index
    ATTR_ACCUM_MODE = Merge List Attributes
    LIST_ATTR = _targetDirectories{}
    ELEMENTS -> Aggregator_4
    <REJECTED> -> Aggregator_4
Aggregator_4
    MODE = Geometry - Assemble One Level
    ORDERED = No
    CONCAT_ATTRS = _TargetDirectories CleanPath_Source
    AGGREGATE_TYPE = Homogeneous Collection (If Possible)
    ACCUM_ATTRS_NAME = Use Attributes From One Feature
    SEP = ", "
    AGGREGATE -> StringConcatenator_3
StringConcatenator_3
    PARM_LINE = Brister i länkning av källa- och målkatalog. Källor: @Value(CleanPath_Source). Mål: @Value(_TargetDirectories). Rejection code: @Value(fme_rejection_code).
    VAL_ATTR = Logg
    ACTION = Create New Attribute
    -> DTStamperYYYY-MM-DD_HH:MI:SS.sss_5
DTStamperYYYY-MM-DD_HH:MI:SS.sss_5
    -> Logg_05
Logg_05: WorkspaceRunner
    BLOCKING = Yes
    WORKSPACE_FILE = $(FME_MF_DIR)_logg.fmw
    WORKSPACE_PARAMETERS = EX_DATE_TIME,@Value(_datetimestamp),EX_PROCESS_NAME,$(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,@Value(ProcessModulName),IsWholeProcessRun,$(IsWholeProcessRun)
Aggregator_2
    MODE = Geometry - Assemble One Level
    ORDERED = No
    CONCAT_ATTRS = text_line_data
    COUNT_ATTR = Antal_target
    AGGREGATE_TYPE = Homogeneous Collection (If Possible)
    ACCUM_ATTRS_NAME = Use Attributes From One Feature
    SEP = ", "
    AGGREGATE -> AttributeCreator_4
AttributeCreator_4
    ATTR_TABLE = SET_TO _id = 1
    -> BulkAttributeRenamer_2
BulkAttributeRenamer_2
    PATTERN_ACTION_DISP = ADDPREFIX
    MODE_CHOICE = RENAME
    REPLACE_STR = Target_
    ATTRCHOICE = All Attributes
    -> FeatureMerger [SUPPLIER]
FeatureMerger
    MERGE_TYPE = Attributes Only
    PROCESS_DUPS = No
    ATTR_ACCUM_MODE = Merge Supplier
    SUPPLIERS_FIRST = No
    IGNORE_NULLS = No
    ATTR_CONFLICT_RES = Use Requestor
    REJECT_NULL_MISSING_KEYS = No
    JOIN_KEYS = @Value(Source__id) @Value(Target__id) AUTO
    MERGED -> StringConcatenator_8
    UNMERGED_REQUESTOR -> Aggregator_3
    UNUSED_SUPPLIER -> Aggregator_3
    <REJECTED> -> StringConcatenator_9
Aggregator_3
    MODE = Geometry - Assemble One Level
    PRESERVE_ID = No
    ORDERED = No
    ID_SELECTION = ID and Parent ID
    ATTR_TO_TRAIT = Yes
    AGGREGATE_TYPE = Homogeneous Collection (If Possible)
    ACCUM_ATTRS_NAME = Use Attributes From One Feature
    SEP = ,
    AGGREGATE -> StringConcatenator_2
StringConcatenator_2
    PARM_LINE = Fel i länkningen mellan repositoryns käll- och målkataloger.
    VAL_ATTR = Exception
    ACTION = Create New Attribute
    -> DTStamperYYYY-MM-DD_HH:MI:SS.sss_3
DTStamperYYYY-MM-DD_HH:MI:SS.sss_3
    -> Logg_03
Logg_03: WorkspaceRunner
    BLOCKING = Yes
    WORKSPACE_FILE = $(FME_MF_DIR)_logg.fmw
    WORKSPACE_PARAMETERS = EX_DATE_TIME,@Value(_datetimestamp),EX_PROCESS_NAME,@Value(Source_ProcessName),EX_ID,@Value(Source_ProcessID),EX_TYPE,ERROR,EX,@Value(Exception),EX_WorkSpace,$(FME_MF_DIR_USERTYPED)$(FME_MF_NAME),EX_ROT_DIRECTORY,@Value(Source_RotDirectory),EX_PROCESS_MODUL_NAME,@Value(Source_ProcessModulName),IsWholeProcessRun,$(IsWholeProcessRun)
StringConcatenator_8
    PARM_LINE = Kör @Value(Source_ProcessName) för @Value(Source_Antal_source) st. repositorykällor (@Value(Source_text_line_data)). Kopieras till @Value(Target_Antal_target) st. målkataloger (@Value(Target_text_line_data)).
    VAL_ATTR = Logg
    ACTION = Create New Attribute
    -> DTStamperYYYY-MM-DD_HH:MI:SS.sss
DTStamperYYYY-MM-DD_HH:MI:SS.sss
    -> Logg_01
Logg_01: WorkspaceRunner
    BLOCKING = No
    WORKSPACE_FILE = $(FME_MF_DIR)_logg.fmw
    WORKSPACE_PARAMETERS = EX_DATE_TIME,@Value(_datetimestamp),EX_PROCESS_NAME,@Value(Source_ProcessName),EX_ID,@Value(Source_ProcessID),EX_TYPE,INFORMATION,EX,@Value(Logg),EX_WorkSpace,$(FME_MF_DIR_USERTYPED)$(FME_MF_NAME),EX_ROT_DIRECTORY,@Value(Source_RotDirectory),EX_PROCESS_MODUL_NAME,@Value(Source_ProcessModulName),IsWholeProcessRun,$(IsWholeProcessRun)
StringConcatenator_9
    PARM_LINE = Statistik för antalet källor och mål för repositorin kan inte beräknas.
    VAL_ATTR = Exception
    ACTION = Create New Attribute
    -> DTStamperYYYY-MM-DD_HH:MI:SS.sss_2
DTStamperYYYY-MM-DD_HH:MI:SS.sss_2
    -> Logg_2
Logg_2: WorkspaceRunner
    BLOCKING = No
    WORKSPACE_FILE = $(FME_MF_DIR)_logg.fmw
    WORKSPACE_PARAMETERS = EX_DATE_TIME,@Value(_datetimestamp),EX_PROCESS_NAME,@Value(Source_ProcessName),EX_ID,@Value(Source_ProcessID),EX_TYPE,VARNING,EX,@Value(Exception),EX_WorkSpace,$(FME_MF_DIR_USERTYPED)$(FME_MF_NAME),EX_ROT_DIRECTORY,@Value(Source_RotDirectory),EX_PROCESS_MODUL_NAME,@Value(Source_ProcessModulName),IsWholeProcessRun,$(IsWholeProcessRun)

FME custom transformer CleansSubTargetDirectories

Parameters:
- _SOURCEDIRECTORIES = @Value(_SourceDirectories)   # Sourcedirectories

DistributionInfo (input)
    -> AttributeSplitter
    -> FeatureMerger [SUPPLIER]
AttributeSplitter
    LIST_NAME = _folders
    DROP_EMPTY_PARTS = Yes
    ATTR_NAME = _SourceDirectories
    DELIMITER = \
    TRIM_OPTION = Both
    -> ListElementCounter
ListConcatenator
    DROP_EMPTY_PARTS = Yes
    VAL_ATTR = _TargetSubDirectories
    SEP = \
    LIST_ATTR = _folders{}._folders
    -> StringConcatenator
ListExploder
    ATTR_CONFLICT_RES = Use List Attribute Values
    INDEX_ATTR = _element_index
    ATTR_ACCUM_MODE = Merge List Attributes
    LIST_ATTR = _folders{}
    ELEMENTS -> AttributeRenamer
    <REJECTED> -> <Rejected> (output)
AttributeRenamer
    ATTR_TABLE = RENAME_SET_DEFAULT _folders > _TargetSubDirectories
    -> StringConcatenator
StringConcatenator
    ATTRLIST = _TargetSubDirectories
    PARM_LINE = @Value(_TargetSubDirectories)\
    ACTION = Overwrite Existing Attributes
    -> FeatureMerger [REQUESTOR]
AttributeCreator_3
    ATTR_TABLE = SET_TO _TargetSubDirectories
    -> FeatureMerger [REQUESTOR]
FeatureMerger
    MERGE_TYPE = Attributes Only
    PROCESS_DUPS = Yes
    ATTR_ACCUM_MODE = Merge Supplier
    SUPPLIERS_FIRST = No
    IGNORE_NULLS = No
    ATTR_CONFLICT_RES = Use Requestor
    CONNECT_Z_MODE = First Wins
    GEOM_TYPE = Build Polygons
    REJECT_NULL_MISSING_KEYS = No
    JOIN_KEYS = @Value(_SourceDirectories) @Value(_SourceDirectories) AUTO
    MERGED -> AttributeRemover
    <REJECTED> -> <Rejected> (output)
AttributeRemover
    REMOVE_ATTRS = FM-ID,_element_index,_element_count
    LIST_ATTRS = _folders{}
    -> Output (output)
Output (output)
<Rejected> (output)

Bookmark: Kontrollerar om kataloger är fler än 1
ListElementCounter
    CNT_ATTR = _element_count
    LIST_NAME = _folders{}
    -> Tester
Tester
    TEST_DESCRIPTION = ""
    TEST_MODE = Automatic
    BOOL_OP = OR
    TEST_CLAUSE = TEST @Value(_element_count) > 1
    PASSED -> ListExploder_3
    FAILED -> AttributeCreator_3

Bookmark: Tar bort sista elementet i listan
ListExploder_3
    ATTR_CONFLICT_RES = Use List Attribute Values
    INDEX_ATTR = _element_index
    ATTR_ACCUM_MODE = Merge List Attributes
    LIST_ATTR = _folders{}
    ELEMENTS -> Sorter
    <REJECTED> -> <Rejected> (output)
Sorter
    SORT_PARM = _element_index NUMERIC ASCENDING
    SORTED -> Tester_3
Note: Alla element utom sista går vidare
Tester_3
    TEST_DESCRIPTION = ""
    TEST_MODE = Automatic
    BOOL_OP = OR
    TEST_CLAUSE = TEST @Value(_element_index) < @Evaluate(@Value(_element_count)-1)
    PASSED -> Aggregator
Aggregator
    MODE = Attributes Only
    ORDERED = No
    LIST_ATTRS_TO_INCLUDE = _folders
    GROUP_BY = _SourceDirectories
    LIST_NAME = _folders
    ACCUM_ATTRS_NAME = Drop Incoming Attributes
    SEP = ,
    AGGREGATE -> ListElementCounter_2

Bookmark: Kontroll om endast 1 element är kvar
ListElementCounter_2
    CNT_ATTR = _element_count
    LIST_NAME = _folders{}
    -> Tester_4
Note: 1 element ska ej skickas / för listkonkatenering
Tester_4
    TEST_DESCRIPTION = ""
    TEST_MODE = Automatic
    BOOL_OP = OR
    TEST_CLAUSE = TEST @Value(_element_count) > 1
    PASSED -> ListConcatenator
    FAILED -> ListExploder

FME custom transformer PathFolderSplitterCleaner

Parameters:
- _REPOSOURCEDIRECTORY = @Value(_RepoSourceDirectory)   # Reposourcedirectory (RSD)
- _SOURCEDIRECTORIES = @Value(_SourceDirectories)   # Sourcedirectories (SD)

Källa (input)
    -> StringLengthCalculator
Tester
    TEST_DESCRIPTION = ""
    TEST_MODE = Automatic
    BOOL_OP = OR
    TEST_CLAUSE = TEST @Value(_RSD_substring_END) = /
    PASSED -> SubstringExtractor_2
    FAILED -> Tester_2
SubstringExtractor_2
    RESULT_ATTR = _RepoSourceDirectory
    SRC_STRING = @Value(_RepoSourceDirectory)
    END = @Value(_RSD_length)-2
    START = 0
    -> StringConcatenator_2
StringConcatenator_2
    ATTRLIST = _RepoSourceDirectory
    PARM_LINE = @Value(_RepoSourceDirectory)\
    ACTION = Overwrite Existing Attributes
    -> StringLengthCalculator_4
Tester_2
    TEST_DESCRIPTION = ""
    TEST_MODE = Automatic
    BOOL_OP = OR
    TEST_CLAUSE = TEST @Value(_SD_substring_START) = /
    PASSED -> SubstringExtractor_3
    FAILED -> TestFilter
SubstringExtractor_3
    RESULT_ATTR = _SourceDirectories
    SRC_STRING = @Value(_SourceDirectories)
    END = 0
    START = 0
    -> StringConcatenator_3
StringConcatenator_3
    ATTRLIST = _SourceDirectories
    PARM_LINE = \@Value(_SourceDirectories)
    ACTION = Overwrite Existing Attributes
    -> StringLengthCalculator_5
TestFilter
    TEST_LIST:
      BOOL_OP,OR,COMPOSITE_TEST,<Unused>,TEST_CLAUSE,"TEST @Value(_RSD_substring_END) = @Value(_SD_substring_START)",\ = \,BOOL_OP,AND,COMPOSITE_TEST,<Unused>,TEST_CLAUSE,"TEST @Value(_RSD_substring_END) != \
      TEST @Value(_SD_substring_START) != \",* = *,BOOL_OP,COMPOSITE,COMPOSITE_TEST,"""(1 AND 2) OR (3 AND 4)""",TEST_CLAUSE,"TEST @Value(_RSD_substring_END) = \
      TEST @Value(_SD_substring_START) != \
      TEST @Value(_RSD_substring_END) != \
      TEST @Value(_SD_substring_START) = \",\ = * | * = \
    DEFAULT_VALUE = <UNFILTERED>
    \ = \ -> SubstringExtractor_4
    * = * -> StringConcatenator_7
    \ = * | * = \ -> StringConcatenator_6
    <UNFILTERED> -> <Rejected> (output)
SubstringExtractor_4
    RESULT_ATTR = _SourceDirectories
    SRC_STRING = @Value(_SourceDirectories)
    END = 0
    START = 0
    -> StringConcatenator_6
StringConcatenator_6
    PARM_LINE = @Value(_RepoSourceDirectory)@Value(_SourceDirectories)
    VAL_ATTR = CleanPath
    ACTION = Create New Attribute
    -> Junction
StringConcatenator_7
    PARM_LINE = @Value(_RepoSourceDirectory)\@Value(_SourceDirectories)
    VAL_ATTR = CleanPath
    ACTION = Create New Attribute
    -> Junction
Junction
    -> AttributeRemover
AttributeRemover
    REMOVE_ATTRS = _RSD_length,_RSD_substring_END,_SD_substring_END,_SD_substring_START,_SD_length
    -> CleanPath (output)
CleanPath (output)
<Rejected> (output)

Bookmark: Teckenlängd sökvägar
StringLengthCalculator
    LENGTH_ATTR = _RSD_length
    SRC_ATTR = _RepoSourceDirectory
    -> StringLengthCalculator_2
StringLengthCalculator_2
    LENGTH_ATTR = _SD_length
    SRC_ATTR = _SourceDirectories
    -> SubstringExtractor_5

Bookmark: Extrahera 1:a och sista tecknet
SubstringExtractor_5
    RESULT_ATTR = _RSD_substring_END
    SRC_STRING = @Value(_RepoSourceDirectory)
    END = @Value(_RSD_length)-1
    START = @Value(_RSD_length)-1
    -> SubstringExtractor_6
SubstringExtractor_6
    RESULT_ATTR = _SD_substring_START
    SRC_STRING = @Value(_SourceDirectories)
    END = 0
    START = 0
    -> SubstringExtractor_7
SubstringExtractor_7
    RESULT_ATTR = _SD_substring_END
    SRC_STRING = @Value(_SourceDirectories)
    END = @Value(_SD_length)-1
    START = @Value(_SD_length)-1
    -> TestFilter_2

Bookmark: Sökväg del processmodul avslut
Note: Sökväg Dataset slut
TestFilter_2
    TEST_LIST:
      BOOL_OP,OR,COMPOSITE_TEST,<Unused>,TEST_CLAUSE,"TEST @Value(_SD_substring_END) = /",/,BOOL_OP,OR,COMPOSITE_TEST,<Unused>,TEST_CLAUSE,"TEST @Value(_SD_substring_END) = \",\,BOOL_OP,AND,COMPOSITE_TEST,<Unused>,TEST_CLAUSE,"TEST @Value(_SD_substring_END) != \
      TEST @Value(_SD_substring_END) != /",!= \ | /
    DEFAULT_VALUE = <UNFILTERED>
    / -> SubstringExtractor
    \ -> StringLengthCalculator_3
    != \ | / -> StringConcatenator
    <UNFILTERED> -> <Rejected> (output)
SubstringExtractor
    RESULT_ATTR = _SourceDirectories
    SRC_STRING = @Value(_SourceDirectories)
    END = @Value(_SD_length)-2
    START = 0
    -> StringConcatenator
StringConcatenator
    ATTRLIST = _SourceDirectories
    PARM_LINE = @Value(_SourceDirectories)\
    ACTION = Overwrite Existing Attributes
    -> StringLengthCalculator_3

Bookmark: SD stränglängd och sista tecknet
StringLengthCalculator_3
    LENGTH_ATTR = _SD_length
    SRC_ATTR = _SourceDirectories
    -> SubstringExtractor_8
SubstringExtractor_8
    RESULT_ATTR = _SD_substring_END
    SRC_STRING = @Value(_SourceDirectories)
    END = @Value(_SD_length)-1
    START = @Value(_SD_length)-1
    -> Tester

Bookmark: RSD stränglängd och sista tecknet
StringLengthCalculator_4
    LENGTH_ATTR = _RSD_length
    SRC_ATTR = _RepoSourceDirectory
    -> SubstringExtractor_9
SubstringExtractor_9
    RESULT_ATTR = _RSD_substring_END
    SRC_STRING = @Value(_RepoSourceDirectory)
    END = @Value(_RSD_length)-1
    START = @Value(_RSD_length)-1
    -> Tester_2

Bookmark: SD stränglängd och första tecknet
StringLengthCalculator_5
    LENGTH_ATTR = _SD_length
    SRC_ATTR = _SourceDirectories
    -> SubstringExtractor_10
SubstringExtractor_10
    RESULT_ATTR = _SD_substring_START
    SRC_STRING = @Value(_SourceDirectories)
    END = 0
    START = 0
    -> TestFilter

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    TIMEZONE = local
    STAMP_TYPE = datetime
    INCLUDE_OFFSET = NO
    DATETIME_ATTR = _dts
    -> DateTimeConverter
DateTimeConverter
    REPAIR_INPUT = NO
    OUT_FORMAT = %Y-%m-%d %H:%M:%S
    DATETIME_ATTR = _dts
    -> AttributeCreator
    <REJECTED> -> <Rejected> (output)
AttributeCreator
    ATTR_TABLE = SET_TO _mils = @Value(_dts)
    -> StringReplacer
StringReplacer
    SRC_ATTRS = _dts
    CASE = NO
    FIND_TEXT = \.\d*
    REGEXP = YES
    NO_MATCH = _FME_NO_OP_
    -> StringReplacer_2
StringReplacer_2
    SRC_ATTRS = _mils
    CASE = NO
    FIND_TEXT = .*\.
    REGEXP = YES
    NO_MATCH = _FME_NO_OP_
    -> SubstringExtractor
SubstringExtractor
    RESULT_ATTR = _subMils
    SRC_STRING = @Value(_mils)
    END = 2
    START = 0
    -> StringConcatenator
StringConcatenator
    PARM_LINE = @Value(_dts).@Value(_subMils)
    VAL_ATTR = _datetimestamp
    ACTION = Create New Attribute
    -> AttributeRemover
AttributeRemover
    REMOVE_ATTRS = _mils,_dts,_subMils
    -> Output (output)
Output (output)
<Rejected> (output)
