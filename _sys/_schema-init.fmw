FME workspace _schema-init.fmw

Parameters:
- RotDirectory = ../   # Katalogen där processen startar
- ProcessName =   # Processnamn
- DataFormat =   # Input Format
- InData = LKR_GIS   # Indata (shape, zip eller databasschema)
- InData-DatabasTable = NULL
- OutputDirectory =   # Katalog för lagring av del av datalager
- OutSchemaFileName = schema-init   # Filnamn för schemalistning
- OutSchemaFileExtention = .xlsx   # Filändelse för schemlistning
- Out = $(OutputDirectory)$(OutSchemaFileName)$(OutSchemaFileExtention)   # Schema-dokumentation

Readers:
- SCHEMA_1: SCHEMA from $(InData)
- ORACLE_SPATIAL_1: ORACLE_SPATIAL from $(InData)

Writers:
- XLSXW_1: XLSXW to $(Out)

Note: Parametrar / * [RotDirectory] Kommer från batch-processen och är obligatoriskt för alla FME-processor. / * [ProcessName] Kommer från batch-processen och är obligatoriskt för alla FME-processor. / * [DataFormat] Styr SchemaReader till vilket format som väntas och hanteras. / * [InData] Fil(er) eller databas (samma benämning behöver vara definierad som databasanslutning) / * [InData-DatabasTable] Om databas skickas in som InData ska tabeller tänkta att användas listas här. Flera tabeller listas med mellanslag. NULL som default-värde för / * [OutputDirectory] Katalogsökväg där schemat skrivs ut till. / Privata / * [OutSchemaFileExtention] Excel-fil 2007 (xlsx). / * [OutSchemaFileName] Filnamn / * [Out] Kompletta sökvägen till fil och den parameter som FME-skrivaren använder. En sammanställning av [OutputDirectory][OutSchemaFileName][OutSchemaFileExtention]
schema (reader SCHEMA_1)
    attributes: fme_feature_type_name varchar(200)
    -> ParameterFetcher
ParameterFetcher
    ATTR_LIST = ProcessName $(ProcessName) RotDirectory $(RotDirectory) InData $(InData) OutputDirectory $(OutputDirectory)
    -> UUIDGenerator_2
UUIDGenerator_2
    UUID_ATTR = ProcessID
    -> ListExploder
    -> ConcatenatedSample [StringAttribute]
ListExploder
    ATTR_ACCUM_MODE = Merge List Attributes
    ATTR_CONFLICT_RES = Use List Attribute Values
    LIST_ATTR = attribute{}
    INDEX_ATTR = _element_index
    ELEMENTS -> AttributeRenamer
    <REJECTED> -> ConcatenatedSample_2 [StringAttribute]
AttributeRenamer
    ATTR_TABLE = RENAME_SET_DEFAULT name > column_name
    -> AttributeCreator
AttributeCreator
    ATTR_TABLE:
      SET_TO dl_need_new_column_name = false
      SET_TO dl_new_column_name
      SET_TO dl_export = true
    -> FilenamePartExtractor
FilenamePartExtractor
    SRC_ATTR = @Value(fme_dataset)
    FULLNAME_ATTR = DatasetFull
    EXTENSION_ATTR = _extension
    DIRNAME_ATTR = _dirname
    ROOTNAME_ATTR = Dataset
    DIRPATH_ATTR = _dirpath
    -> StringLengthCalculator
Note: Beräknar längd kolumnnamn
StringLengthCalculator
    SRC_ATTR = column_name
    LENGTH_ATTR = column_name_char_length
    -> Tester
AttributeCopier
    ATTR_TABLE = COPY column_name > dl_new_column_name = @Value(column_name)
    -> AttributeCreator_2_OUTPUT
AttributeCreator_2_OUTPUT: Junction
    -> FeatureHolder
FeatureHolder
    -> Sampler
    -> schema (writer XLSXW_1)
schema (writer XLSXW_1)
    attributes: fme_feature_type_name string(20), column_name auto(20), dl_need_new_column_name auto(20), dl_new_column_name auto(20), dl_export string(20), fme_data_type auto(20), native_data_type auto(20), fme_format_long_name string(20), fme_format_short_name string(20), _dirpath auto(20), _extension auto(20), DatasetFull auto(20), Dataset auto(20), column_name_char_length auto(20)

Bookmark: Markerar för långa kolumnnamn för Shape
Tester
    BOOL_OP = AND
    TEST_CLAUSE = TEST @Value(column_name_char_length) > 10
    TEST_DESCRIPTION = ""
    TEST_MODE = Automatic
    PASSED -> AttributeCreator_2
    FAILED -> AttributeCopier
AttributeCreator_2
    ATTR_TABLE = SET_TO dl_need_new_column_name = true
    -> AttributeCreator_2_OUTPUT

Bookmark: Loggning
Sampler
    RATE = 1
    SAMPLE_MODE = No
    SAMPLE_TYPE_LONG = First N Features
    SAMPLED -> StringConcatenator_7
StringConcatenator_7
    ACTION = Create New Attribute
    VAL_ATTR = Logg
    PARM_LINE = Schema-dokumentation "$(OutSchemaFileName)$(OutSchemaFileExtention)" skapad under "$(OutputDirectory)".
    -> TimeStamper_6
TimeStamper_6
    TIME_ATTR = Timestamp
    FMT = ^Y-^m-^d ^H:^M:^S
    -> Logg_7
Logg_7: WorkspaceRunner
    BLOCKING = No
    WORKSPACE_PARAMETERS = EX_DATE_TIME,@Value(Timestamp),EX_PROCESS_NAME,@Value(ProcessName),EX_ID,@Value(ProcessID),EX_TYPE,KLART,EX,@Value(Logg),EX_WorkSpace,$(FME_MF_DIR_USERTYPED)$(FME_MF_NAME),EX_ROT_DIRECTORY,@Value(RotDirectory)
    WORKSPACE_FILE = $(FME_MF_DIR)_logg.fmw
ConcatenatedSample_2
    FME_DATASET = @Value(fme_dataset)
    NumberToShorten = 3
    StringConcatenatedSample -> StringConcatenator_3
StringConcatenator_3
    ACTION = Create New Attribute
    VAL_ATTR = Logg
    PARM_LINE = Följande, @Value(fme_dataset_concatenated), dataset kunde inte kolumninformation utläsas ifrån (totalt @Value(TotaltAntal) st.).
    -> TimeStamper_3
TimeStamper_3
    TIME_ATTR = Timestamp
    FMT = ^Y-^m-^d ^H:^M:^S
    -> Logg_3
Logg_3: WorkspaceRunner
    BLOCKING = No
    WORKSPACE_PARAMETERS = EX_DATE_TIME,@Value(Timestamp),EX_PROCESS_NAME,@Value(ProcessName),EX_ID,@Value(ProcessID),EX_TYPE,VARNING,EX,@Value(Logg),EX_WorkSpace,$(FME_MF_DIR_USERTYPED)$(FME_MF_NAME),EX_ROT_DIRECTORY,@Value(RotDirectory)
    WORKSPACE_FILE = $(FME_MF_DIR)_logg.fmw
ConcatenatedSample
    FME_DATASET = @Value(fme_dataset)
    NumberToShorten = 3
    StringConcatenatedSample -> StringConcatenator_2
StringConcatenator_2
    ACTION = Create New Attribute
    VAL_ATTR = Logg
    PARM_LINE = Kartlägger schemastruktur för dataseten @Value(fme_dataset_concatenated) (totalt @Value(TotaltAntal) st.) efter inparametern "@Value(InData)".
    -> TimeStamper_2
TimeStamper_2
    TIME_ATTR = Timestamp
    FMT = ^Y-^m-^d ^H:^M:^S
    -> Logg_2
Logg_2: WorkspaceRunner
    BLOCKING = No
    WORKSPACE_PARAMETERS = EX_DATE_TIME,@Value(Timestamp),EX_PROCESS_NAME,@Value(ProcessName),EX_ID,@Value(ProcessID),EX_TYPE,INFORMATION,EX,@Value(Logg),EX_WorkSpace,$(FME_MF_DIR_USERTYPED)$(FME_MF_NAME),EX_ROT_DIRECTORY,@Value(RotDirectory)
    WORKSPACE_FILE = $(FME_MF_DIR)_logg.fmw

FME custom transformer ConcatenatedSample

Parameters:
- FME_DATASET = @Value(fme_dataset)   # Attribute to Sample Concatenate
- NumberToShorten = 3   # Antal innan förkortning

StringAttribute (input)
    -> Aggregator
Aggregator
    ORDERED = No
    COUNT_ATTR = TotaltAntal
    LIST_ATTRS_TO_INCLUDE = fme_dataset
    SEP = ,
    MODE = Geometry - Assemble One Level
    LIST_NAME = dataset
    GROUP_BY = fme_dataset
    ACCUM_ATTRS_NAME = Use Attributes From One Feature
    AGGREGATE_TYPE = Homogeneous Collection (If Possible)
    AGGREGATE -> Tester_2
Tester_2
    BOOL_OP = OR
    TEST_CLAUSE = TEST @Value(TotaltAntal) < 3
    TEST_DESCRIPTION = ""
    TEST_MODE = Automatic
    PASSED -> ListIndexer
    FAILED -> ListConcatenator
ListIndexer
    INDEX = 0
    LIST_ATTR = dataset{}
    PREFIX = _ds0_
    -> ListIndexer_2
ListIndexer_2
    INDEX = 1
    LIST_ATTR = dataset{}
    PREFIX = _ds1_
    -> ListIndexer_3
ListIndexer_3
    INDEX = @Value(TotaltAntal)-1
    LIST_ATTR = dataset{}
    PREFIX = _dsn_
    -> StringConcatenator
StringConcatenator
    ACTION = Create New Attribute
    VAL_ATTR = fme_dataset_concatenated
    PARM_LINE = @Value(_ds0_fme_dataset), @Value(_ds1_fme_dataset), ... , @Value(_dsn_fme_dataset)
    -> StringConcatenator_OUTPUT_-__StringConcatenator_Output
ListConcatenator
    DROP_EMPTY_PARTS = No
    VAL_ATTR = fme_dataset_concatenated
    LIST_ATTR = dataset{}.fme_dataset
    SEP = ", "
    -> StringConcatenator_OUTPUT_-__StringConcatenator_Output
StringConcatenator_OUTPUT_-__StringConcatenator_Output: Junction
    -> AttributeRemover
AttributeRemover
    LIST_ATTRS = dataset{} dataset{}.fme_dataset
    REMOVE_ATTRS = fme_dataset,_ds1_fme_dataset,_dsn_fme_dataset,dataset{0}.fme_dataset,_ds0_fme_dataset
    -> StringConcatenatedSample (output)
StringConcatenatedSample (output)
