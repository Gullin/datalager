FME workspace _emailer-send-error.fmw

Parameters:
- RotDirectory = C:\Dev\Datalager_procsrc/   # Katalogen där processen startar
- ProcessName =   # Processnamn
- ProcessModulName =   # Processmodulsnamn
- IsWholeProcessRun = 1   # Är hela datalagerprocessen körd
- EmailHost =   # Host e-postserver
- EmailPort =   # Port e-postserver
- EmailFrom =   # From
- EmailTo =   # To
- EmailCC = [NO CC]   # CC

HTMLReportGenerator
    CONTENT_LIST = HEADER HEADER HEADER HTML TABLE HTML SEPARATOR HTML HTML HTML
    PAGE_CONFIG = HEADER{{TEXT;Fel i datalager!;HEADER;H3;HEADER_ID;;ALIGNMENT;LEFT;COLOR;0,0,0;FME_CONTROLLER_QUERY_FILE;transformers\dependencies\html5\Header.fme;FME_CONTROLLER_CHOICE;Header}}HEADER{{TEXT;Processen för uppbyggnad av datalager rapporterar fel.;HEADER;H4;HEADER_ID;;ALIGNMENT;LEFT;COLOR;0,0,0;FME_CONTROLLER_QUERY_FILE;transformers\dependencies\html5\Header.fme;FME_CONTROLLER_CHOICE;Header}}HEADER{{TEXT;Läs i följande bifogade filer för mer detaljer:;HEADER;H4;HEADER_ID;;ALIGNMENT;LEFT;COLOR;0,0,0;FME_CONTROLLER_QUERY_FILE;transformers\dependencies\html5\Header.fme;FME_CONTROLLER_CHOICE;Header}}HTML{{HTML;<br/>;FME_CONTROLLER_QUERY_FILE;transformers\dependencies\html5\Custom HTML.fme;FME_CONTROLLER_CHOICE;Custom HTML}}TABLE{{STYLE;STRIPED;TABLE;_fil|Fil/_beskrivning|Beskrivning;FME_CONTROLLER_QUERY_FILE;transformers\dependencies\html5\Table.fme;FME_CONTROLLER_CHOICE;Table}}HTML{{HTML;<br/>;FME_CONTROLLER_QUERY_FILE;transformers\dependencies\html5\Custom HTML.fme;FME_CONTROLLER_CHOICE;Custom HTML}}SEPARATOR{{WIDTH;1;FME_CONTROLLER_QUERY_FILE;transformers\dependencies\html5\Separator.fme;FME_CONTROLLER_CHOICE;Separator}}HTML{{HTML;<br/>;FME_CONTROLLER_QUERY_FILE;transformers\dependencies\html5\Custom HTML.fme;FME_CONTROLLER_CHOICE;Custom HTML}}HTML{{HTML;Förekommer inte ovan filer indikeras avsaknade med en "dummy"-fil med filändelsen ".missing". Vilken fil som saknas framgår av filnamnet.;FME_CONTROLLER_QUERY_FILE;transformers\dependencies\html5\Custom HTML.fme;FME_CONTROLLER_CHOICE;Custom HTML}}HTML{{HTML;Från 2023-06-13 stöds inte loggning till Excel-dokument p.g.a. återkommande behörighetskonflikter. SQLite ersätter som format. Läses av FME eller förslagsvis open source programmet "DB Browser for SQLite".;FME_CONTROLLER_QUERY_FILE;transformers/dependencies/html5/Custom HTML.fme;FME_CONTROLLER_CHOICE;Custom HTML}}
    -> AttributeCreator_6
AttributeCreator_6
    ATTR_TABLE = SET_TO _merge_ID = 1
    -> FeatureMerger [SUPPLIER]
Creator
    GEOMTYPE = Geometry Object
    NUM = 1
    CREATED -> ParameterFetcher_2
ParameterFetcher_2
    ATTR_LIST = RotDirectory $(RotDirectory) _ProcessName $(ProcessName) _ProcessModulName $(ProcessModulName) _IsWholeProcessRun $(IsWholeProcessRun) _EmailHost $(EmailHost) _EmailPort $(EmailPort) _EmailFrom $(EmailFrom) _EmailTo $(EmailTo) _EmailCC $(EmailCC)
    -> UUIDGenerator_3
UUIDGenerator_3
    UUID_ATTR = ProcessID
    -> Tester_2
    -> StringConcatenator_8
Tester_2
    BOOL_OP = OR
    TEST_CLAUSE = TEST @Value(_EmailCC) != [NO CC]
    TEST_MODE = Automatic
    PASSED -> AttributeCreator_2
    FAILED -> AttributeCreator_7
AttributeCreator_7
    ATTR_TABLE = SET_TO _EmailCC
    -> AttributeCreator_2
AttributeCreator_2
    ATTR_TABLE = SET_TO _merge_ID = 1
    -> StringConcatenator_2
StringConcatenator_2
    ACTION = Create New Attribute
    PARM_LINE = @Value(RotDirectory)_log\BatchEventLog.log
    VAL_ATTR = _path_batcheventlogg
    -> StringConcatenator
StringConcatenator
    ACTION = Create New Attribute
    PARM_LINE = fme_basicstring:20%25:@Value(RotDirectory)_log\DatalagerLogg.sqlite
    VAL_ATTR = _path_datalagerlogg
    -> AttributeCreator
AttributeCreator
    ATTR_TABLE = SET_TO _subject = [ ERROR ] Datalager
    -> Tester
Tester
    BOOL_OP = OR
    TEST_CLAUSE = TEST @Value(_IsWholeProcessRun) = 0
    TEST_MODE = Automatic
    PASSED -> StringConcatenator_6
    FAILED -> StringConcatenator_4
StringConcatenator_6
    ACTION = Create New Attribute
    PARM_LINE = @Value(RotDirectory)@Value(_ProcessModulName)\_log\FATAL_ERROR.log
    VAL_ATTR = _path_fatal_error
    -> StringConcatenator_7
StringConcatenator_7
    ACTION = Create New Attribute
    PARM_LINE = @Value(_subject), processmodul @Value(_ProcessModulName)
    VAL_ATTR = _subject
    -> Junction
StringConcatenator_4
    ACTION = Create New Attribute
    PARM_LINE = @Value(RotDirectory)_log\FATAL_ERROR.log
    VAL_ATTR = _path_fatal_error
    -> Junction
Junction
    -> FeatureMerger [REQUESTOR]
FeatureMerger
    ATTR_ACCUM_MODE = Merge Supplier
    ATTR_CONFLICT_RES = Use Requestor
    IGNORE_NULLS = No
    JOIN_KEYS = @Value(_merge_ID) @Value(_merge_ID) AUTO
    MERGE_TYPE = Attributes Only
    PROCESS_DUPS = No
    REJECT_NULL_MISSING_KEYS = No
    SUPPLIERS_FIRST = No
    MERGED -> FileExistenceReplacer
FileExistenceReplacer
    _MERGE_ID = @Value(_merge_ID)
    _PATH_BATCHEVENTLOGG = @Value(_path_batcheventlogg)
    _PATH_DATALAGERLOGG = @Value(_path_datalagerlogg)
    _PATH_FATAL_ERROR = @Value(_path_fatal_error)
    -> FeatureHolder
FeatureHolder
    -> Emailer
Emailer
    ATTACHMENTTABLE = @Value(_path_batcheventlogg)  autodetect @Value(_path_datalagerlogg)  autodetect @Value(_path_fatal_error)  autodetect
    BODY = @Value(html_content)
    CC = @Value(_EmailCC)
    FROM = @Value(_EmailFrom)
    SERVICE = Generic SMTP
    SMTP_CONNECTION = SMTP_GROUP;;HOST;@Value(_EmailHost);PORT;@Value(_EmailPort);ENCRYPTION;None;TIMEOUT;60;AUTHENTICATION;NO;USERNAME;<Unused>;PASSWORD;<Unused>;FME_CONTROLLER_QUERY_FILE;transformers\dependencies\emailer\Generic SMTP.fme
    SUBJECT = @Value(_subject)
    TO = @Value(_EmailTo)
    Sent -> StringConcatenator_3
    <REJECTED> -> StringConcatenator_5

Bookmark: Beskrivning bifogade filer
Creator_2
    GEOMTYPE = Geometry Object
    NUM = 3
    CREATED -> Sampler
    CREATED -> Sampler_2
    CREATED -> Sampler_3
Sampler
    RATE = 1
    SAMPLE_MODE = No
    SAMPLE_TYPE_LONG = First N Features
    SAMPLED -> AttributeCreator_3
AttributeCreator_3
    ATTR_TABLE:
      SET_TO _fil = BatchEventLog.log
      SET_TO _beskrivning = Filen redogör för händelser i batch-processen.
    -> HTMLReportGenerator
Sampler_2
    RATE = 2
    SAMPLE_MODE = No
    SAMPLE_TYPE_LONG = Every Nth Feature
    SAMPLED -> AttributeCreator_4
AttributeCreator_4
    ATTR_TABLE:
      SET_TO _fil = DatalagerLogg.sqlite
      SET_TO _beskrivning = Filen redogör för händelser i FME-processerna.
    -> HTMLReportGenerator
Sampler_3
    RATE = 3
    SAMPLE_MODE = No
    SAMPLE_TYPE_LONG = Every Nth Feature
    SAMPLED -> AttributeCreator_5
AttributeCreator_5
    ATTR_TABLE:
      SET_TO _fil = FATAL_ERROR.log
      SET_TO _beskrivning = Fel som orsakat meddelande.
    -> HTMLReportGenerator

Bookmark: Loggning
StringConcatenator_5
    ACTION = Create New Attribute
    PARM_LINE = E-post kunde inte skickas. Felkod: @Value(fme_rejection_code)
    VAL_ATTR = Exception
    -> DTStamperYYYY-MM-DD_HH:MI:SS.sss_2
DTStamperYYYY-MM-DD_HH:MI:SS.sss_2
    -> Logg_04
Logg_04: WorkspaceRunner
    BLOCKING = Yes
    WORKSPACE_FILE = $(FME_MF_DIR)_logg.fmw
    WORKSPACE_PARAMETERS = EX_DATE_TIME,@Value(_datetimestamp),EX_PROCESS_NAME,$(ProcessName),EX_ID,@Value(ProcessID),EX_TYPE,ERROR,EX,@Value(Exception),EX_WorkSpace,$(FME_MF_DIR_USERTYPED)$(FME_MF_NAME),EX_ROT_DIRECTORY,@Value(RotDirectory),EX_PROCESS_MODUL_NAME,$(ProcessModulName),IsWholeProcessRun,$(IsWholeProcessRun)
StringConcatenator_3
    ACTION = Create New Attribute
    PARM_LINE = E-post skickad
    VAL_ATTR = Logg
    -> DTStamperYYYY-MM-DD_HH:MI:SS.sss_3
DTStamperYYYY-MM-DD_HH:MI:SS.sss_3
    -> Logg_05
Logg_05: WorkspaceRunner
    BLOCKING = Yes
    WORKSPACE_FILE = $(FME_MF_DIR)_logg.fmw
    WORKSPACE_PARAMETERS = EX_DATE_TIME,@Value(_datetimestamp),EX_PROCESS_NAME,$(ProcessName),EX_ID,@Value(ProcessID),EX_TYPE,KLART,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
StringConcatenator_8
    ACTION = Create New Attribute
    PARM_LINE = "Kör "
    VAL_ATTR = Logg
    -> DTStamperYYYY-MM-DD_HH:MI:SS.sss
DTStamperYYYY-MM-DD_HH:MI:SS.sss
    -> Logg_01
Logg_01: WorkspaceRunner
    BLOCKING = No
    WORKSPACE_FILE = $(FME_MF_DIR)_logg.fmw
    WORKSPACE_PARAMETERS = EX_DATE_TIME,@Value(_datetimestamp),EX_PROCESS_NAME,$(ProcessName),EX_ID,@Value(ProcessID),EX_TYPE,INFORMATION,EX,@Value(Logg),EX_WorkSpace,$(FME_MF_DIR_USERTYPED)$(FME_MF_NAME),EX_ROT_DIRECTORY,$(RotDirectory),EX_PROCESS_MODUL_NAME,$(ProcessModulName),IsWholeProcessRun,$(IsWholeProcessRun)

FME custom transformer FileExistenceReplacer

Parameters:
- _PATH_BATCHEVENTLOGG = @Value(_path_batcheventlogg)   # Path Batcheventlogg
- _PATH_DATALAGERLOGG = @Value(_path_datalagerlogg)   # Path Datalagerlogg
- _PATH_FATAL_ERROR = @Value(_path_fatal_error)   # Path Fatal Error
- _MERGE_ID = @Value(_merge_ID)   # Merge Id

Input (input)
    -> FilenamePartExtractor_2
Output (output)

Bookmark: batcheventlogg
FilenamePartExtractor_2
    DIRNAME_ATTR = _dirname
    DIRPATH_ATTR = _dirpath
    EXTENSION_ATTR = _extension
    FULLNAME_ATTR = _filename
    ROOTNAME_ATTR = _rootname
    SRC_ATTR = @Value(_path_batcheventlogg)
    -> FeatureReader_2 [INITIATOR]
    -> FeatureMerger [REQUESTOR]
FeatureReader_2
    ATTR_ACCUM_MODE = Only Use Result
    COMBINE_GEOM = Use Result
    DATASET = @Value(_dirpath)
    FORMAT = PATH
    OUTPUT_FEATURES_DISPLAY = Schema and Data Features
    PATH_GLOB_PATTERN = @Value(_filename)
    PATH_RETRIEVE_FILE_PROPERTIES = NO
    PATH_TYPE = ANY
    PATH__OFFSET_DATETIME = yes
    <OTHER> -> AttributeCreator
AttributeCreator
    ATTR_TABLE = SET_TO _batcheventlogg_exists = 1
    -> AttributeCreator_7
AttributeCreator_7
    ATTR_TABLE = SET_TO _merge_ID = 1
    -> FeatureMerger [SUPPLIER]
FeatureMerger
    ATTR_ACCUM_MODE = Merge Supplier
    ATTR_CONFLICT_RES = Use Requestor
    IGNORE_NULLS = No
    JOIN_KEYS = @Value(_merge_ID) @Value(_merge_ID) AUTO
    MERGE_TYPE = Attributes Only
    PROCESS_DUPS = No
    REJECT_NULL_MISSING_KEYS = No
    SUPPLIERS_FIRST = No
    MERGED -> Junction_3
    UNMERGED_REQUESTOR -> AttributeCreator_2
AttributeCreator_2
    ATTR_TABLE = SET_TO _batcheventlogg_exists = 0
    -> TempPathnameCreator
TempPathnameCreator
    BASENAME = file-BatchEventLog
    EXTENSION = missing
    PATHNAME_ATTR = _file_not_exists
    -> AttributeCreator_8
AttributeCreator_8
    ATTR_TABLE = SET_TO _path_batcheventlogg = @Value(_file_not_exists)
    -> Junction_3
    -> FeatureWriter_3 [text_line]
Junction_3
    -> FilenamePartExtractor_3
FeatureWriter_3
    DATASET = @Value(_path_batcheventlogg)
    DATASET_ATTR = _dataset
    FEATURE_TYPE_LIST_ATTR = _feature_type
    FORMAT = TEXTLINE
    TEXTLINE_DESTINATION_DATASETTYPE_VALIDATION = Yes
    TEXTLINE_ENCODING = SYSTEM
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written

Bookmark: datalagerlogg
FilenamePartExtractor_3
    DIRNAME_ATTR = _dirname
    DIRPATH_ATTR = _dirpath
    EXTENSION_ATTR = _extension
    FULLNAME_ATTR = _filename
    ROOTNAME_ATTR = _rootname
    SRC_ATTR = @Value(_path_datalagerlogg)
    -> FeatureReader_3 [INITIATOR]
    -> FeatureMerger_2 [REQUESTOR]
FeatureReader_3
    ATTR_ACCUM_MODE = Only Use Result
    COMBINE_GEOM = Use Result
    DATASET = @Value(_dirpath)
    FORMAT = PATH
    OUTPUT_FEATURES_DISPLAY = Schema and Data Features
    PATH_GLOB_PATTERN = @Value(_filename)
    PATH_RETRIEVE_FILE_PROPERTIES = NO
    PATH_TYPE = ANY
    PATH__OFFSET_DATETIME = yes
    <OTHER> -> AttributeCreator_3
AttributeCreator_3
    ATTR_TABLE = SET_TO _datalagerlogg_exists = 1
    -> AttributeCreator_9
AttributeCreator_9
    ATTR_TABLE = SET_TO _merge_ID = 1
    -> FeatureMerger_2 [SUPPLIER]
FeatureMerger_2
    ATTR_ACCUM_MODE = Merge Supplier
    ATTR_CONFLICT_RES = Use Requestor
    IGNORE_NULLS = No
    JOIN_KEYS = @Value(_merge_ID) @Value(_merge_ID) AUTO
    MERGE_TYPE = Attributes Only
    PROCESS_DUPS = No
    REJECT_NULL_MISSING_KEYS = No
    SUPPLIERS_FIRST = No
    MERGED -> Junction
    UNMERGED_REQUESTOR -> AttributeCreator_4
AttributeCreator_4
    ATTR_TABLE = SET_TO _datalagerlogg_exists = 0
    -> TempPathnameCreator_2
TempPathnameCreator_2
    BASENAME = file-DatalagerLogg
    EXTENSION = missing
    PATHNAME_ATTR = _file_not_exists
    -> AttributeCreator_11
AttributeCreator_11
    ATTR_TABLE = SET_TO _path_datalagerlogg = @Value(_file_not_exists)
    -> Junction
    -> FeatureWriter_2 [text_line]
Junction
    -> FilenamePartExtractor_4
FeatureWriter_2
    DATASET = @Value(_path_datalagerlogg)
    DATASET_ATTR = _dataset
    FEATURE_TYPE_LIST_ATTR = _feature_type
    FORMAT = TEXTLINE
    TEXTLINE_DESTINATION_DATASETTYPE_VALIDATION = Yes
    TEXTLINE_ENCODING = SYSTEM
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written

Bookmark: fatal_error
FilenamePartExtractor_4
    DIRNAME_ATTR = _dirname
    DIRPATH_ATTR = _dirpath
    EXTENSION_ATTR = _extension
    FULLNAME_ATTR = _filename
    ROOTNAME_ATTR = _rootname
    SRC_ATTR = @Value(_path_fatal_error)
    -> FeatureReader_4 [INITIATOR]
    -> FeatureMerger_3 [REQUESTOR]
FeatureReader_4
    ATTR_ACCUM_MODE = Only Use Result
    COMBINE_GEOM = Use Result
    DATASET = @Value(_dirpath)
    FORMAT = PATH
    OUTPUT_FEATURES_DISPLAY = Schema and Data Features
    PATH_GLOB_PATTERN = @Value(_filename)
    PATH_RETRIEVE_FILE_PROPERTIES = NO
    PATH_TYPE = ANY
    PATH__OFFSET_DATETIME = yes
    <OTHER> -> AttributeCreator_5
AttributeCreator_5
    ATTR_TABLE = SET_TO _fatal_error_exists = 1
    -> AttributeCreator_10
AttributeCreator_10
    ATTR_TABLE = SET_TO _merge_ID = 1
    -> FeatureMerger_3 [SUPPLIER]
FeatureMerger_3
    ATTR_ACCUM_MODE = Merge Supplier
    ATTR_CONFLICT_RES = Use Requestor
    IGNORE_NULLS = No
    JOIN_KEYS = @Value(_merge_ID) @Value(_merge_ID) AUTO
    MERGE_TYPE = Attributes Only
    PROCESS_DUPS = No
    REJECT_NULL_MISSING_KEYS = No
    SUPPLIERS_FIRST = No
    MERGED -> Junction_2
    UNMERGED_REQUESTOR -> AttributeCreator_6
AttributeCreator_6
    ATTR_TABLE = SET_TO _fatal_error_exists = 0
    -> TempPathnameCreator_4
TempPathnameCreator_4
    BASENAME = file-FATAL_ERROR
    EXTENSION = missing
    PATHNAME_ATTR = _file_not_exists
    -> AttributeCreator_12
AttributeCreator_12
    ATTR_TABLE = SET_TO _path_fatal_error = @Value(_file_not_exists)
    -> FeatureWriter [text_line]
    -> Junction_2
Junction_2
    -> Output (output)
FeatureWriter
    DATASET = @Value(_path_fatal_error)
    DATASET_ATTR = _dataset
    FEATURE_TYPE_LIST_ATTR = _feature_type
    FORMAT = TEXTLINE
    TEXTLINE_DESTINATION_DATASETTYPE_VALIDATION = Yes
    TEXTLINE_ENCODING = SYSTEM
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    INCLUDE_OFFSET = NO
    STAMP_TYPE = datetime
    TIMEZONE = local
    -> DateTimeConverter
DateTimeConverter
    DATETIME_ATTR = _dts
    OUT_FORMAT = %Y-%m-%d %H:%M:%S
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    NO_MATCH = _FME_NO_OP_
    REGEXP = YES
    SRC_ATTRS = _dts
    -> StringReplacer_2
StringReplacer_2
    CASE = NO
    FIND_TEXT = .*\.
    NO_MATCH = _FME_NO_OP_
    REGEXP = YES
    SRC_ATTRS = _mils
    -> SubstringExtractor
SubstringExtractor
    END = 2
    RESULT_ATTR = _subMils
    SRC_STRING = @Value(_mils)
    START = 0
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)
