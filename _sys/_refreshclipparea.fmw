FME workspace _refreshclipparea.fmw

Parameters:
- RotDirectory = ../   # Katalogen där processen startar
- ProcessName =   # Processnamn
- ProcessModulName =   # Processmodulsnamn
- RepositoryRotDir =   # Rotkatalog repository
- ProcessModuleClippArea =   # Processmodul som genererar underlagsdata
- DistSourceFile =   # Filnamn som loggar subkataloger under repo
- IsWholeProcessRun = 1   # Är hela datalagerprocessen körd

Creator
    GEOMTYPE = Geometry Object
    NUM = 1
    CREATED -> ParameterFetcher_2
ParameterFetcher_2
    ATTR_LIST = RotDirectory $(RotDirectory) ProcessName $(ProcessName) ProcessModulName $(ProcessModulName) RepositoryRotDir $(RepositoryRotDir) ProcessModuleClippArea $(ProcessModuleClippArea) DistSourceFile $(DistSourceFile)
    -> UUIDGenerator_2
UUIDGenerator_2
    UUID_ATTR = ProcessID
    -> StringConcatenator_5
    -> FeatureMerger_2 [SUPPLIER]
    -> StringConcatenator_14
StringConcatenator_14
    ACTION = Create New Attribute
    PARM_LINE = fme_basicstring:20%30%6%22:@Value(RotDirectory)@Value(ProcessModuleClippArea)/_log/@Value(DistSourceFile)
    VAL_ATTR = _pathDistSoureFile
    -> FeatureReader_2 [INITIATOR]
FeatureReader_2
    ATTRS_TO_EXPOSE = text_line_data
    ATTR_ACCUM_MODE = Merge Initiator and Result
    ATTR_CONFLICT_RES = Use Result
    ATTR_IGNORE_NULLS = No
    COMBINE_GEOM = Use Result
    DATASET = @Value(_pathDistSoureFile)
    FORMAT = TEXTLINE
    OUTPUT_FEATURES_DISPLAY = Data Features
    TEXTLINE_CREATE_FEATURE_TABLES_FROM_DATA = Yes
    TEXTLINE_ENCODING = windows-1252
    TEXTLINE_READ_BOTTOM_UP = No
    TEXTLINE_READ_WHOLE_FILE_AT_ONCE = NO
    TEXTLINE_SKIP_FOOTER = 0
    TEXTLINE_SKIP_LINES = 0
    <OTHER> -> Tester_5
    <REJECTED> -> Aggregator_4
Tester_5
    BOOL_OP = OR
    TEST_CLAUSE = TEST text_line_data ATTRIBUTE_HAS_A_VALUE ""
    TEST_MODE = TEST
    PASSED -> AttributeTrimmer
    FAILED -> Aggregator_5
AttributeTrimmer
    SRC_ATTRS = text_line_data
    TRIM_CHARS = " "
    TRIM_TO_NONE = Yes
    TRIM_TYPE = Both
    -> StringConcatenator_15
StringConcatenator_15
    ACTION = Create New Attribute
    PARM_LINE = fme_basicstring:20%24%1%22%1:@Value(RotDirectory)@Value(RepositoryRotDir)/@Value(text_line_data)/
    VAL_ATTR = _pathRotClippArea
    -> AttributeCreator
    -> AttributeCreator_2
    -> AttributeCreator_3
AttributeCreator
    ATTR_TABLE = SET_TO FeatureCoordSys = sweref991330
    -> StringConcatenator_16
AttributeCreator_2
    ATTR_TABLE = SET_TO FeatureCoordSys = sweref99tm
    -> StringConcatenator_16
AttributeCreator_3
    ATTR_TABLE = SET_TO FeatureCoordSys = wgs84_latlong
    -> StringConcatenator_16
StringConcatenator_16
    ACTION = Create New Attribute
    PARM_LINE = fme_basicstring:25%23%6:@Value(_pathRotClippArea)@Value(FeatureCoordSys)/*.shp
    VAL_ATTR = _pathFileClippArea
    -> FeatureReader_4 [INITIATOR]
FeatureReader_4
    ATTR_ACCUM_MODE = Merge Initiator and Result
    ATTR_CONFLICT_RES = Use Result
    ATTR_IGNORE_NULLS = No
    COMBINE_GEOM = Use Result
    DATASET = @Value(_pathFileClippArea)
    FORMAT = SHAPEFILE
    INTERACT = NONE
    OUTPUT_FEATURES_DISPLAY = Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_READ_NUMERIC_PADDING_AS = ZERO
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    <OTHER> -> AttributeExposer_2
    <REJECTED> -> Aggregator_6
AttributeExposer_2
    ATTR_LIST = fme_feature_type
    -> StatisticsCalculator
StatisticsCalculator
    CALCULATION_MODE = NUMERIC
    FEAT_STATS = text_line_data,NUMERIC_MODE,,,COUNT,,,,,,,,,,
    COMPLETE -> Tester_6
Tester_6
    BOOL_OP = OR
    TEST_CLAUSE = TEST @Value(text_line_data.total_count) > 1
    TEST_MODE = TEST
    PASSED -> TestFilter
    FAILED -> Aggregator_7
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(fme_feature_type) CONTAINS kommun",kommun,"BOOL_OP,OR,COMPOSITE_TEST,""""""1"""""",TEST_CLAUSE,CASE_INSENSITIVE_TEST @Value(fme_feature_type) CONTAINS lan",lan
    kommun -> AttributeExposer_3
    lan -> AttributeExposer_4
AttributeExposer_3
    ATTR_LIST = kommunkod
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(kommunkod) IN 1283,1214,1261",krans,"BOOL_OP,OR,COMPOSITE_TEST,""""""1"""""",TEST_CLAUSE,TEST @Value(kommunkod) = 1282",landskrona
    krans -> Dissolver
    krans -> Dissolver_2
    landskrona -> Dissolver_2
    landskrona -> AttributeCreator_6
Dissolver
    ACCUM_INPUT_ATTRS = Use Attributes From One Feature
    CLEANING_TOLERANCE = Automatic
    CONNECT_Z_MODE = First Wins
    DEAGGREGATE_INPUT = Yes
    AREA -> AttributeCreator_4
    <REJECTED> -> Aggregator_8
AttributeCreator_4
    ATTR_TABLE = SET_TO Namn = Krans
    -> Junction
Dissolver_2
    ACCUM_INPUT_ATTRS = Use Attributes From One Feature
    CLEANING_TOLERANCE = Automatic
    CONNECT_Z_MODE = First Wins
    DEAGGREGATE_INPUT = Yes
    AREA -> AttributeCreator_5
    <REJECTED> -> Aggregator_9
AttributeCreator_5
    ATTR_TABLE = SET_TO Namn = LandskronaKrans
    -> Junction
AttributeCreator_6
    ATTR_TABLE = SET_TO Namn = Landskrona
    -> Junction
AttributeExposer_4
    ATTR_LIST = lanskod
    -> Tester_4
Tester_4
    BOOL_OP = OR
    TEST_CLAUSE = TEST @Value(lanskod) = 12
    TEST_MODE = TEST
    PASSED -> AttributeCreator_7
AttributeCreator_7
    ATTR_TABLE = SET_TO Namn = Skane
    -> Junction
Junction
    -> Bufferer
Bufferer
    ANGLE = 22.5
    CAP_STYLE = Arc
    CORNER_STYLE = Arc
    MODE = AREA
    OFFSET = 5
    OFFSET_UNITS = NONE
    PRECISION = APPROX
    BUFFERED -> AttributeValueMapper
AttributeValueMapper
    LUT = sweref99tm,SW99TM,sweref991330,SW991330,wgs84_latlong,WGS84_LATLONG
    MAPPING_DIRECTION = FORWARD
    SRC = FeatureCoordSys
    VAL_ATTR = Projektion
    -> AttributeKeeper
AttributeKeeper
    CREATE_BULK_MODE_FEATURES = NO
    KEEP_ATTRS = Namn,Projektion
    -> FeatureWriter_2 [Output]
FeatureWriter_2
    DATASET = $(RotDirectory)_sys/KlippytorSweref99TM1330_skane-krans-lkr_buff5m.ffs
    DATASET_ATTR = _dataset
    FEATURE_TYPE_LIST_ATTR = _feature_types
    FFS_COORDINATE_SYSTEM_GRANULARITY = FEATURE
    FFS_DESTINATION_DATASETTYPE_VALIDATION = No
    FFS_FILE_DEST_DATASET = yes
    FFS_INDEXED = Yes
    FFS_REQUIRES_FEATURE_TABLES = No
    FFS_STORE_SCANNED_METADATA = No
    FFS_STORE_SCANNED_SCHEMA = No
    FORMAT = FFS
    TOTAL_FEATURES_WRITTEN_ATTR = _total_features_written
    SUMMARY -> FeatureMerger_2 [REQUESTOR]

Bookmark: Loggning
Aggregator_8
    ACCUM_ATTRS_NAME = Drop Incoming Attributes
    AGGREGATE_TYPE = Homogeneous Collection (If Possible)
    CONCAT_ATTRS = fme_rejection_code
    GROUP_BY = ProcessID ProcessName RotDirectory
    MODE = Geometry - Assemble One Level
    SEP = "\n"
    AGGREGATE -> StringConcatenator_9
StringConcatenator_9
    ACTION = Create New Attribute
    PARM_LINE:
      fme_basicstring:42%1%26:Fel vid upplösning av ytor för Krans. Fel:
      @Value(fme_rejection_code)
    VAL_ATTR = Logg
    -> DTStamperYYYY-MM-DD_HH:MI:SS.sss_7
DTStamperYYYY-MM-DD_HH:MI:SS.sss_7
    -> Logg_8
Logg_8: WorkspaceRunner
    BLOCKING = No
    MAX_TO_BATCH = 1
    WORKSPACE_FILE = $(FME_MF_DIR)_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Aggregator_9
    ACCUM_ATTRS_NAME = Drop Incoming Attributes
    AGGREGATE_TYPE = Homogeneous Collection (If Possible)
    CONCAT_ATTRS = fme_rejection_code
    GROUP_BY = ProcessID ProcessName RotDirectory
    MODE = Geometry - Assemble One Level
    SEP = "\n"
    AGGREGATE -> StringConcatenator_2
StringConcatenator_2
    ACTION = Create New Attribute
    PARM_LINE:
      fme_basicstring:52%1%26:Fel vid upplösning av ytor för LandskronaKrans. Fel:
      @Value(fme_rejection_code)
    VAL_ATTR = Logg
    -> DTStamperYYYY-MM-DD_HH:MI:SS.sss_2
DTStamperYYYY-MM-DD_HH:MI:SS.sss_2
    -> Logg_3
Logg_3: WorkspaceRunner
    BLOCKING = No
    MAX_TO_BATCH = 1
    WORKSPACE_FILE = $(FME_MF_DIR)_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_13
StringConcatenator_13
    ACTION = Create New Attribute
    PARM_LINE = fme_basicstring:15%16%22%31%12:Klippytor för "@Value(_dataset)" skapades med totalt @Value(_total_features_written) st. objekt.
    VAL_ATTR = Logg
    -> DTStamperYYYY-MM-DD_HH:MI:SS.sss_10
DTStamperYYYY-MM-DD_HH:MI:SS.sss_10
    -> Logg_11
Logg_11: WorkspaceRunner
    BLOCKING = No
    MAX_TO_BATCH = 1
    WORKSPACE_FILE = $(FME_MF_DIR)_logg.fmw
    WORKSPACE_PARAMETERS = EX_DATE_TIME,@Value(_datetimestamp),EX_PROCESS_NAME,@Value(ProcessName),EX_ID,@Value(ProcessID),EX_TYPE,KLART,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Aggregator_7
    ACCUM_ATTRS_NAME = Drop Incoming Attributes
    AGGREGATE_TYPE = Homogeneous Collection (If Possible)
    GROUP_BY = ProcessID ProcessName RotDirectory _pathFileClippArea
    MODE = Geometry - Assemble One Level
    AGGREGATE -> Aggregator_3
Aggregator_3
    ACCUM_ATTRS_NAME = Drop Incoming Attributes
    AGGREGATE_TYPE = Homogeneous Collection (If Possible)
    CONCAT_ATTRS = _pathFileClippArea
    GROUP_BY = ProcessID ProcessName RotDirectory
    MODE = Geometry - Assemble One Level
    SEP = ", "
    AGGREGATE -> StringConcatenator_8
StringConcatenator_8
    ACTION = Create New Attribute
    PARM_LINE:
      fme_basicstring:63%1%26:Ingen data att gå vidare med för att skapa klippytor gällande:
      @Value(_pathFileClippArea)
    VAL_ATTR = Logg
    -> DTStamperYYYY-MM-DD_HH:MI:SS.sss_6
DTStamperYYYY-MM-DD_HH:MI:SS.sss_6
    -> Logg_7
Logg_7: WorkspaceRunner
    BLOCKING = No
    MAX_TO_BATCH = 1
    WORKSPACE_FILE = $(FME_MF_DIR)_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Aggregator_6
    ACCUM_ATTRS_NAME = Drop Incoming Attributes
    AGGREGATE_TYPE = Homogeneous Collection (If Possible)
    CONCAT_ATTRS = _reader_error
    GROUP_BY = ProcessID ProcessName RotDirectory _pathFileClippArea
    MODE = Geometry - Assemble One Level
    SEP = "\n"
    AGGREGATE -> StringConcatenator_7
StringConcatenator_7
    ACTION = Create New Attribute
    PARM_LINE:
      fme_basicstring:33%26%8%1%21:Fel vid läsning av dataset från "@Value(_pathFileClippArea)". Fel:
      @Value(_reader_error)
    VAL_ATTR = Logg
    -> DTStamperYYYY-MM-DD_HH:MI:SS.sss_5
DTStamperYYYY-MM-DD_HH:MI:SS.sss_5
    -> Logg_6
Logg_6: WorkspaceRunner
    BLOCKING = No
    MAX_TO_BATCH = 1
    WORKSPACE_FILE = $(FME_MF_DIR)_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Aggregator_5
    ACCUM_ATTRS_NAME = Drop Incoming Attributes
    AGGREGATE_TYPE = Homogeneous Collection (If Possible)
    COUNT_ATTR = antal
    GROUP_BY = ProcessID ProcessName RotDirectory _pathDistSoureFile
    MODE = Geometry - Assemble One Level
    AGGREGATE -> StringConcatenator_6
StringConcatenator_6
    ACTION = Create New Attribute
    PARM_LINE = fme_basicstring:14%26%13%13%61:Följande fil "@Value(_pathDistSoureFile)" innehåller @Value(antal) st. rader utan information om var data ska hämtas från repo.
    VAL_ATTR = Logg
    -> DTStamperYYYY-MM-DD_HH:MI:SS.sss_4
DTStamperYYYY-MM-DD_HH:MI:SS.sss_4
    -> Logg_5
Logg_5: WorkspaceRunner
    BLOCKING = No
    MAX_TO_BATCH = 1
    WORKSPACE_FILE = $(FME_MF_DIR)_logg.fmw
    WORKSPACE_PARAMETERS = EX_DATE_TIME,@Value(_datetimestamp),EX_PROCESS_NAME,@Value(ProcessName),EX_ID,@Value(ProcessID),EX_TYPE,VARNING,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Aggregator_4
    ACCUM_ATTRS_NAME = Drop Incoming Attributes
    AGGREGATE_TYPE = Homogeneous Collection (If Possible)
    CONCAT_ATTRS = _reader_error
    GROUP_BY = ProcessID ProcessName RotDirectory _pathDistSoureFile
    MODE = Geometry - Assemble One Level
    SEP = "\n"
    AGGREGATE -> StringConcatenator_4
StringConcatenator_4
    ACTION = Create New Attribute
    PARM_LINE:
      fme_basicstring:20%26%7%1%21:Fel vid läsning av "@Value(_pathDistSoureFile)" Fel:
      @Value(_reader_error)
    VAL_ATTR = Logg
    -> DTStamperYYYY-MM-DD_HH:MI:SS.sss_3
DTStamperYYYY-MM-DD_HH:MI:SS.sss_3
    -> Logg_4
Logg_4: WorkspaceRunner
    BLOCKING = No
    MAX_TO_BATCH = 1
    WORKSPACE_FILE = $(FME_MF_DIR)_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
StringConcatenator_5
    ACTION = Create New Attribute
    PARM_LINE = Kör @Value(ProcessName) för nedladdning av data definierad i "[TOMT]" till datalagret.
    VAL_ATTR = Logg
    -> DTStamperYYYY-MM-DD_HH:MI:SS.sss
DTStamperYYYY-MM-DD_HH:MI:SS.sss
    -> Logg_2
Logg_2: WorkspaceRunner
    BLOCKING = No
    MAX_TO_BATCH = 1
    WORKSPACE_FILE = $(FME_MF_DIR)_logg.fmw
    WORKSPACE_PARAMETERS = EX_DATE_TIME,@Value(_datetimestamp),EX_PROCESS_NAME,@Value(ProcessName),EX_ID,@Value(ProcessID),EX_TYPE,INFORMATION,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    INCLUDE_OFFSET = NO
    STAMP_TYPE = datetime
    TIMEZONE = local
    -> DateTimeConverter
DateTimeConverter
    DATETIME_ATTR = _dts
    OUT_FORMAT = %Y-%m-%d %H:%M:%S
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    NO_MATCH = _FME_NO_OP_
    REGEXP = YES
    SRC_ATTRS = _dts
    -> StringReplacer_2
StringReplacer_2
    CASE = NO
    FIND_TEXT = .*\.
    NO_MATCH = _FME_NO_OP_
    REGEXP = YES
    SRC_ATTRS = _mils
    -> SubstringExtractor
SubstringExtractor
    END = 2
    RESULT_ATTR = _subMils
    SRC_STRING = @Value(_mils)
    START = 0
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)
