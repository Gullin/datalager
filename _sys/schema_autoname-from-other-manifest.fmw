FME workspace schema_autoname-from-other-manifest.fmw

Parameters:
- SourceDataset_XLSXR = C:\dev\Datalager_procsrc\lkr-postgis-td_baskarta\_schema\schema-manifest.xlsx   # Source Microsoft Excel File(s)
- SourceDataset_XLSXR_3 = C:\dev\Datalager_procsrc\lkr-postgis-td_detaljplan\_schema\schema-init.xlsx   # Source Microsoft Excel File(s)
- OutputFolder = $(FME_MF_DIR_USERTYPED)$(FME_MF_NAME)_schema-autonamed   # Katalog fil ska skrivas
- DestDataset_XLSXW = $(OutputFolder)/$(OutputFileName)   # Destination Microsoft Excel File
- OutputFileName = schema-init-autonamed.xlsx   # Filnamn schemafil

Readers:
- XLSXR_1: XLSXR from $(SourceDataset_XLSXR)
- XLSXR_2: XLSXR from $(SourceDataset_XLSXR_3)

Writers:
- XLSXW_1: XLSXW to $(DestDataset_XLSXW)

schema (reader XLSXR_2)
    attributes: filter_fme_feature_type char(17), filter_export_column char(10), fme_feature_type_name char(39), column_name char(25), dl_need_new_column_name char(6), dl_new_column_name char(11), dl_export char(5), fme_data_type char(18), native_data_type char(14), fme_format_long_name char(8), fme_format_short_name char(8), _dirpath char(1), _extension char(1), DatasetFull char(11), Dataset char(11), column_name_char_length number(3,0)
    -> Tester
Tester
    BOOL_OP = OR
    TEST_CLAUSE = TEST dl_new_column_name ATTRIBUTE_IS_EMPTY ""
    PASSED -> FeatureMerger [REQUESTOR]
    FAILED -> Junction
schema (reader XLSXR_1)
    attributes: filter_fme_feature_type char(17), filter_export_column char(10), fme_feature_type_name char(35), column_name char(31), dl_need_new_column_name char(6), dl_new_column_name char(11), dl_export char(5), fme_data_type char(18), native_data_type char(14), fme_format_long_name char(8), fme_format_short_name char(8), _dirpath char(1), _extension char(1), DatasetFull char(11), Dataset char(11), column_name_char_length number(3,0)
    -> Aggregator
Aggregator
    ACCUM_ATTRS_NAME = Use Attributes From One Feature
    AGGREGATE_TYPE = Homogeneous Collection (If Possible)
    GROUP_BY = dl_new_column_name column_name
    MODE = Geometry - Assemble One Level
    ORDERED = No
    SEP = ,
    AGGREGATE -> FeatureMerger [SUPPLIER]
FeatureMerger
    ATTR_ACCUM_MODE = Prefix Supplier
    IGNORE_NULLS = No
    JOIN_KEYS = @Value(column_name) @Value(column_name) AUTO
    MERGE_TYPE = Attributes Only
    PROCESS_DUPS = NO
    REJECT_NULL_MISSING_KEYS = No
    SUPPLIERS_FIRST = No
    SUPPLIER_PREFIX = sup_
    MERGED -> FeatureMerger_Merged
    MERGED -> AttributeManager
    UNMERGED_REQUESTOR -> FeatureMerger_UnmergedRequestor
    UNMERGED_REQUESTOR -> Junction
    USED_SUPPLIER -> FeatureMerger_UsedSupplier
    UNUSED_SUPPLIER -> FeatureMerger_UnusedSupplier
    <REJECTED> -> FeatureMerger__Rejected_
AttributeManager
    ATTR_TABLE:
      SET_TO dl_new_column_name = @Value(sup_dl_new_column_name)
      REMOVE sup_column_name
      REMOVE sup_dl_new_column_name
      REMOVE sup_filter_fme_feature_type
      REMOVE sup_filter_export_column
      REMOVE sup_fme_feature_type_name
      REMOVE sup_dl_need_new_column_name
      REMOVE sup_dl_export
      REMOVE sup_fme_data_type
      REMOVE sup_native_data_type
      REMOVE sup_fme_format_long_name
      REMOVE sup_fme_format_short_name
      REMOVE sup__dirpath
      REMOVE sup__extension
      REMOVE sup_DatasetFull
      REMOVE sup_Dataset
      REMOVE sup_column_name_char_length
    -> Junction
Junction
    -> schema (writer XLSXW_1)
schema (writer XLSXW_1)
    attributes: filter_fme_feature_type string(17), filter_export_column string(10), fme_feature_type_name string(39), column_name string(25), dl_need_new_column_name string(6), dl_new_column_name string(11), dl_export string(5), fme_data_type string(18), native_data_type string(14), fme_format_long_name string(8), fme_format_short_name string(8), _dirpath string(1), _extension string(1), DatasetFull string(11), Dataset string(11), column_name_char_length number(3)
FeatureMerger_Merged: Inspector
FeatureMerger_UnmergedRequestor: Inspector
FeatureMerger_UsedSupplier: Inspector
FeatureMerger_UnusedSupplier: Inspector
FeatureMerger__Rejected_: Inspector
