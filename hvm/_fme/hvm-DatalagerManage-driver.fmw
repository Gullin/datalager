FME workspace hvm-DatalagerManage-driver.fmw

Parameters:
- FME_USER_PARAM_PRIVATE_GRP =
- FeatureListFile =
- IsWholeProcessRun =
- Manifest =
- OutputDirectory =
- PG_SCHEMA =
- ProcessModulName =
- ProcessName =
- RotDirectory =
- SchemaFlush =

Note: Parametrar / * [RotDirectory] Kommer från batch-processen och är obligatoriskt för alla FME-processor. / * [ProcessName] Kommer från batch-processen och är obligatoriskt för alla FME-processor. / * [Manifest] Excel-fil från ett tidigare exporterat schema anpassad med nya kolumnnamn samt vilken data som ska exporteras. / * [OutputDirectory] Katalogsökväg för exporterad geodata (delrepository).
Creator_2
    GEOMTYPE = Geometry Object
    NUM = 1
    CREATED -> ParameterFetcher_3
    CREATED -> FeatureReader [INITIATOR]
ParameterFetcher_3
    ATTR_LIST = ProcessName $(ProcessName) RotDirectory $(RotDirectory) ProcessModulName $(ProcessModulName)
    -> UUIDGenerator_3
UUIDGenerator_3
    UUID_ATTR = ProcessID
    -> FeatureReader_2 [INITIATOR]
    -> FeatureMerger_7 [SUPPLIER]
    -> Sampler_2
FeatureReader_2
    ATTRIBUTES = CSV,"col0,col1,col2,col3"
    ATTR_ACCUM_MODE = Only Use Result
    COMBINE_GEOM = Use Result
    CSV2_CASE_SENSITIVE_FIELD_NAMES = Yes
    CSV2_DATA_START_LINE = 1
    CSV2_DELIMITER = |
    CSV2_ENCODING = ibm437
    CSV2_ENFORCE_STRICT_SCHEMA = No
    CSV2_FEATURE_TYPE_NAME = FORMAT_NAME
    CSV2_PRESERVE_SOURCE_ENCODING = No
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = $(RotDirectory)$(ProcessName)/_schema/$(FeatureListFile)
    FORMAT = CSV2
    INTERACT = <No Spatial Filter>
    OUTPUT_FEATURES_DISPLAY = Data Features
    CSV -> FeatureMerger_7 [REQUESTOR]
FeatureMerger_7
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Tester
Note: Plockar bort kommentarer och tomma rader
Tester
    BOOL_OP = COMPOSITE
    COMPOSITE_TEST = "1 OR ((2 OR 3) AND (4 OR 5 OR 6) AND (7 OR 8 OR 9) AND (10 OR 11 OR 12))"
    TEST_CLAUSE:
      TEST @Value(col0) BEGINS_WITH ;
      TEST col0 ATTRIBUTE_VALUE_NULL ""
      TEST col0 ATTRIBUTE_IS_EMPTY ""
      TEST col1 ATTRIBUTE_VALUE_NULL ""
      TEST col1 ATTRIBUTE_IS_EMPTY ""
      TEST col1 ATTRIBUTE_IS_MISSING ""
      TEST col2 ATTRIBUTE_VALUE_NULL ""
      TEST col2 ATTRIBUTE_IS_EMPTY ""
      TEST col2 ATTRIBUTE_IS_MISSING ""
      TEST col3 ATTRIBUTE_VALUE_NULL ""
      TEST col3 ATTRIBUTE_IS_EMPTY ""
      TEST col3 ATTRIBUTE_IS_MISSING ""
    TEST_MODE = Automatic
    FAILED -> FeatureMerger_8 [REQUESTOR]
FeatureReader
    ATTRIBUTES = schema,"filter_fme_feature_type,filter_export_column,fme_feature_type_name,column_name,dl_need_new_column_name,dl_new_column_name,dl_export,fme_data_type,native_data_type,fme_format_long_name,fme_format_short_name,_dirpath,_extension,DatasetFull,Dataset,column_name_char_length"
    ATTR_ACCUM_MODE = Only Use Result
    COMBINE_GEOM = Use Result
    DATASET = $(Manifest)
    FORMAT = XLSXR
    INTERACT = NONE
    OUTPUT_FEATURES_DISPLAY = Schema and Data Features
    XLSXR_ALLOW_DOLLAR_SIGNS = YES
    XLSXR_CASE_SENSITIVE_FEATURE_TYPES = YES
    XLSXR_CONFIGURATION_DATASET = $(Manifest)
    XLSXR_CREATE_FEATURE_TABLES_FROM_DATA = Yes
    XLSXR_EXCEL_COL_NAMES = YES
    XLSXR_EXPAND_MERGED_CELLS = Yes
    XLSXR_FORCE_DATETIME = NO
    XLSXR_KEEP_SCHEMA_SETTINGS = YES
    XLSXR_QUERY_FEATURE_TYPES_FOR_MERGE_FILTERS = Yes
    XLSXR_READ_BLANK_AS = Missing
    XLSXR_READ_RASTER_MODE = None
    XLSXR_SCAN_SCHEMA_IF_DYNAMIC = No
    XLSXR_SCHEMA = schema,0,filter_fme_feature_type,char,17,,,1,filter_export_column,char,10,,,2,fme_feature_type_name,char,60,,,3,column_name,char,11,,,4,dl_need_new_column_name,char,6,,,5,dl_new_column_name,char,11,,,6,dl_export,char,6,,,7,fme_data_type,char,18,,,8,native_data_type,char,11,,,9,fme_format_long_name,char,15,,,10,fme_format_short_name,char,14,,,11,_dirpath,char,70,,,12,_extension,char,5,,,13,DatasetFull,char,15,,,14,Dataset,char,10,,,15,column_name_char_length,number,3," 0",,1,,,,NO,NO,1,$(Manifest),"0,0,15,1714",,NO,NO
    XLSXR_STRIP_SHEETNAME_SPACES = YES
    XLSXR_TABLELIST = schema
    XLSXR_TRIM_ATTR_NAME_WHITESPACE = Yes
    XLSXR_USE_SCHEMA_OTHER_FILES = No
    schema -> Tester_5
Tester_5
    BOOL_OP = OR
    COMPOSITE_TEST = 1
    TEST_CLAUSE = TEST @Value(dl_export) = true
    TEST_MODE = TEST
    PASSED -> TestFilter_2
    PASSED -> Tester_2
Note: Format som stöds
TestFilter_2
    DEFAULT_VALUE = <UNFILTERED>
    TEST_LIST = "BOOL_OP,OR,COMPOSITE_TEST,""""""1"""""",TEST_CLAUSE,TEST @Value(fme_format_short_name) = WFS",WFS
    WFS -> StringConcatenator_10
    <UNFILTERED> -> Aggregator
StringConcatenator_10
    ACTION = Overwrite Existing Attributes
    ATTRLIST = _dirpath
    PARM_LINE = fme_basicstring:16%19:@Value(_dirpath)@Value(DatasetFull)
    -> Aggregator_6
Aggregator_6
    ACCUM_ATTRS_NAME = Drop Incoming Attributes
    GROUP_BY = _dirpath fme_feature_type_name
    MODE = Attributes Only
    AGGREGATE -> FeatureMerger_8 [SUPPLIER]
FeatureMerger_8
    ATTR_ACCUM_MODE = Merge Supplier
    ATTR_CONFLICT_RES = Use Requestor
    IGNORE_NULLS = No
    JOIN_KEYS = @Value(col1) @Value(_dirpath) AUTO @Value(col0) @Value(fme_feature_type_name) AUTO
    MERGE_TYPE = Attributes Only
    PROCESS_DUPS = NO
    REJECT_NULL_MISSING_KEYS = No
    SUPPLIERS_FIRST = No
    MERGED -> WorkspaceRunner
    UNMERGED_REQUESTOR -> Aggregator_11
    UNUSED_SUPPLIER -> Aggregator_9
    <REJECTED> -> Aggregator_7
WorkspaceRunner
    BLOCKING = Yes
    WORKSPACE_FILE = $(FME_MF_DIR)hvm-DatalagerManage-main.fmw
    WORKSPACE_PARAMETERS = RotDirectory,$(RotDirectory),ProcessName,$(ProcessName),OutputDirectory,$(OutputDirectory),ProcessModulName,$(ProcessModulName),IsWholeProcessRun,$(IsWholeProcessRun),SchemaFlush,$(SchemaFlush),PG_SCHEMA,$(PG_SCHEMA),InData,@Value(_dirpath),InData-DatabaseTable,@Value(fme_feature_type_name),InData_Alternative,@Value(col2),DestDataset_POSTGIS,PG_DATALAGER,DestDataset_POSTGIS_14,PG_DATALAGER_ADMSRV0118
    SUCCEEDED -> Aggregator_5
    FAILED -> StringConcatenator_3
    SUMMARY -> FeatureMerger [SUPPLIER]
Creator
    GEOMTYPE = Geometry Object
    NUM = 1
    CREATED -> ParameterFetcher_2
ParameterFetcher_2
    ATTR_LIST = ProcessName $(ProcessName) RotDirectory $(RotDirectory)
    -> StringConcatenator_8
StringConcatenator_8
    ACTION = Create New Attribute
    PARM_LINE = @Value(ProcessName)_DRIVER
    VAL_ATTR = ProcessName_DRIVER
    -> UUIDGenerator_2
UUIDGenerator_2
    UUID_ATTR = ProcessID
    -> AttributeCreator_12_OUTPUT_-__FeatureMerger_3_SUPPLIER
AttributeCreator_12_OUTPUT_-__FeatureMerger_3_SUPPLIER: Junction
    -> Junction
    -> Junction_3
    -> Junction_5
    -> Junction_7
    -> Junction_9
    -> Junction_11
    -> Junction_13
    -> Junction_15
Note: FeatureMerger_2 : Supplier
Junction
    -> Junction_2
Note: FeatureMerger_3 : Supplier
Junction_3
    -> Junction_4
Note: FeatureMerger_4 : Supplier
Junction_5
    -> Junction_6
Note: FeatureMerger_5 : Supplier
Junction_7
    -> Junction_8
Note: FeatureMerger_6 : Supplier
Junction_9
    -> Junction_10
Note: FeatureMerger_10 : Supplier
Junction_11
    -> Junction_12
Note: FeatureMerger_11 : Supplier
Junction_13
    -> Junction_14
Note: FeatureMerger_9 : Supplier
Junction_15
    -> Junction_16

Bookmark: Loggning
Note: Endast till för som signal att starta logg
Sampler_2
    RATE = 1
    SAMPLE_MODE = No
    SAMPLE_TYPE_LONG = First N Features
    SAMPLED -> FeatureMerger_2 [REQUESTOR]
StringConcatenator_3
    ACTION = Create New Attribute
    PARM_LINE = fme_basicstring:16%1%29:@Value(_dirpath).@Value(fme_feature_type_name)
    VAL_ATTR = _result
    -> FeatureMerger_5 [REQUESTOR]
Sampler_5
    RATE = 1
    SAMPLE_MODE = No
    SAMPLE_TYPE_LONG = First N Features
    SAMPLED -> FeatureMerger_6 [REQUESTOR]
Note: I schemamanifest men inte _modul_settings_dataset.ini
Aggregator_9
    ACCUM_ATTRS_NAME = Use Attributes From One Feature
    AGGREGATE_TYPE = Homogeneous Collection (If Possible)
    CONCAT_ATTRS = fme_feature_type_name
    GROUP_BY = _dirpath
    MODE = Geometry - Assemble One Level
    ORDERED = No
    SEP = ", "
    AGGREGATE -> StringConcatenator_13
StringConcatenator_13
    ACTION = Create New Attribute
    PARM_LINE = fme_basicstring:16%2%29:@Value(_dirpath); @Value(fme_feature_type_name)
    VAL_ATTR = _result
    -> Aggregator_10
Aggregator_10
    ACCUM_ATTRS_NAME = Use Attributes From One Feature
    AGGREGATE_TYPE = Homogeneous Collection (If Possible)
    CONCAT_ATTRS = _result
    MODE = Geometry - Assemble One Level
    ORDERED = No
    SEP = ", "
    AGGREGATE -> FeatureMerger_10 [REQUESTOR]
Note: I _modul_settings_dataset.ini men inte schemamanifest
Aggregator_11
    ACCUM_ATTRS_NAME = Use Attributes From One Feature
    AGGREGATE_TYPE = Homogeneous Collection (If Possible)
    CONCAT_ATTRS = col0
    GROUP_BY = col1
    MODE = Geometry - Assemble One Level
    ORDERED = No
    SEP = ", "
    AGGREGATE -> StringConcatenator_14
StringConcatenator_14
    ACTION = Create New Attribute
    PARM_LINE = fme_basicstring:12%2%12:@Value(col1); @Value(col0)
    VAL_ATTR = _result
    -> Aggregator_12
Aggregator_12
    ACCUM_ATTRS_NAME = Use Attributes From One Feature
    AGGREGATE_TYPE = Homogeneous Collection (If Possible)
    CONCAT_ATTRS = _result
    MODE = Geometry - Assemble One Level
    ORDERED = No
    SEP = ", "
    AGGREGATE -> FeatureMerger_11 [REQUESTOR]
Aggregator_7
    ACCUM_ATTRS_NAME = Use Attributes From One Feature
    AGGREGATE_TYPE = Homogeneous Collection (If Possible)
    GROUP_BY = fme_rejection_code
    MODE = Geometry - Assemble One Level
    ORDERED = No
    SEP = ", "
    AGGREGATE -> Aggregator_8
Aggregator_8
    ACCUM_ATTRS_NAME = Use Attributes From One Feature
    AGGREGATE_TYPE = Homogeneous Collection (If Possible)
    CONCAT_ATTRS = fme_rejection_code
    MODE = Geometry - Assemble One Level
    ORDERED = No
    SEP = ", "
    AGGREGATE -> FeatureMerger_9 [REQUESTOR]
Note: Format som det ej finns stöd för men som är / definierade som exporterbara i manifest
Aggregator
    ACCUM_ATTRS_NAME = Use Attributes From One Feature
    AGGREGATE_TYPE = Homogeneous Collection (If Possible)
    COUNT_ATTR = Antal
    GROUP_BY = fme_format_short_name
    MODE = Geometry - Assemble One Level
    ORDERED = No
    SEP = ", "
    AGGREGATE -> FeatureMerger_4 [REQUESTOR]
Note: Följande kolumn förekommer fler än / en gång för specifikt dataset
Aggregator_4
    ACCUM_ATTRS_NAME = Use Attributes From One Feature
    AGGREGATE_TYPE = Homogeneous Collection (If Possible)
    COUNT_ATTR = Antal
    GROUP_BY = dl_new_column_name
    MODE = Geometry - Assemble One Level
    ORDERED = No
    SEP = ", "
    AGGREGATE -> FeatureMerger_3 [REQUESTOR]
Note: AttributeCreator_12_-_FeatureMerger_3
Junction_2
    -> FeatureMerger_2 [SUPPLIER]
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_2
StringConcatenator_2
    ACTION = Create New Attribute
    PARM_LINE = Kör @Value(ProcessName_DRIVER) för data definierad i "" till datalagret.
    VAL_ATTR = Logg
    -> DTStamperYYYY-MM-DD_HH:MI:SS.sss
DTStamperYYYY-MM-DD_HH:MI:SS.sss
    -> Logg_2
Logg_2: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,INFORMATION,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: AttributeCreator_12_-_FeatureMerger_3
Junction_4
    -> FeatureMerger_3 [SUPPLIER]
FeatureMerger_3
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_6
StringConcatenator_6
    ACTION = Create New Attribute
    PARM_LINE = Följande @Value(Antal)  st. kolumner finns det dubbletter för (@Value(dl_new_column_name)). För att exporterad data vara läsbar enligt manifest, ändra kolumnnamn i manifest.
    VAL_ATTR = Logg
    -> DTStamperYYYY-MM-DD_HH:MI:SS.sss_2
DTStamperYYYY-MM-DD_HH:MI:SS.sss_2
    -> Logg_3
Logg_3: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: AttributeCreator_12_-_FeatureMerger_3
Junction_6
    -> FeatureMerger_4 [SUPPLIER]
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_4
StringConcatenator_4
    ACTION = Create New Attribute
    PARM_LINE = Följande @Value(Antal)  st. format stöds ej (@Value(fme_format_short_name)). För att export ska vara fullt möjligt enligt manifest, ändra i manifest eller definiera ny WorkspaceRunner med workspace.
    VAL_ATTR = Logg
    -> DTStamperYYYY-MM-DD_HH:MI:SS.sss_3
DTStamperYYYY-MM-DD_HH:MI:SS.sss_3
    -> Logg_4
Logg_4: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: AttributeCreator_12_-_FeatureMerger_3
Junction_8
    -> FeatureMerger_5 [SUPPLIER]
FeatureMerger_5
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_7
StringConcatenator_7
    ACTION = Create New Attribute
    PARM_LINE = @Value(_result) - kunde inte exporteras. Fel: @Value(_failure_message)
    VAL_ATTR = Logg
    -> DTStamperYYYY-MM-DD_HH:MI:SS.sss_4
DTStamperYYYY-MM-DD_HH:MI:SS.sss_4
    -> Logg_6
Logg_6: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: AttributeCreator_12_-_FeatureMerger_3
Junction_10
    -> FeatureMerger_6 [SUPPLIER]
StringConcatenator_5
    ACTION = Create New Attribute
    PARM_LINE = Kör @Value(ProcessName_DRIVER) för data definierad i "" till datalagret.
    VAL_ATTR = Logg
    -> DTStamperYYYY-MM-DD_HH:MI:SS.sss_5
DTStamperYYYY-MM-DD_HH:MI:SS.sss_5
    -> Logg_5
Logg_5: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,KLART,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: AttributeCreator_12_OUTPUT_-__FeatureMerger_3_SUPPLIER : Output
Junction_12
    -> FeatureMerger_10 [SUPPLIER]
FeatureMerger_10
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_11
StringConcatenator_11
    ACTION = Create New Attribute
    PARM_LINE:
      fme_basicstring:84%1%8%1%15:Motsvarande dataset i schemamanifest saknas för innehåll _modul-settings-dataset.ini
      Berörda:
      @Value(_result)
    VAL_ATTR = Logg
    -> DTStamperYYYY-MM-DD_HH:MI:SS.sss_7
DTStamperYYYY-MM-DD_HH:MI:SS.sss_7
    -> Logg_8
Logg_8: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,VARNING,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: AttributeCreator_12_OUTPUT_-__FeatureMerger_3_SUPPLIER : Output
Junction_14
    -> FeatureMerger_11 [SUPPLIER]
FeatureMerger_11
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_12
StringConcatenator_12
    ACTION = Create New Attribute
    PARM_LINE:
      fme_basicstring:73%1%8%1%15:Motsvarande dataset i _modul-settings-dataset.ini saknas i schemamanifest
      Berörda:
      @Value(_result)
    VAL_ATTR = Logg
    -> DTStamperYYYY-MM-DD_HH:MI:SS.sss_8
DTStamperYYYY-MM-DD_HH:MI:SS.sss_8
    -> Logg_9
Logg_9: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,VARNING,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: AttributeCreator_12_OUTPUT_-__FeatureMerger_3_SUPPLIER : Output
Junction_16
    -> FeatureMerger_9 [SUPPLIER]
FeatureMerger_9
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_9
StringConcatenator_9
    ACTION = Create New Attribute
    PARM_LINE:
      fme_basicstring:87%1%14%1%26:Innehåll i _modul-settings-dataset.ini kunde inte länkas mot schemamanifest för dataset
      Felmeddelande:
      @Value(fme_rejection_code)
    VAL_ATTR = Logg
    -> DTStamperYYYY-MM-DD_HH:MI:SS.sss_6
DTStamperYYYY-MM-DD_HH:MI:SS.sss_6
    -> Logg_7
Logg_7: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)

Bookmark: Sammanställning Succeeded och Summary
Aggregator_5
    ACCUM_ATTRS_NAME = Use Attributes From One Feature
    AGGREGATE_TYPE = Homogeneous Collection (If Possible)
    COUNT_ATTR = AntalSuccess
    MODE = Geometry - Assemble One Level
    ORDERED = No
    SEP = ,
    AGGREGATE -> FeatureMerger [REQUESTOR]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Sampler_5

Bookmark: Kontrollera om kolumnnamn förekommer fler än en gång per dataset
Tester_2
    BOOL_OP = AND
    TEST_CLAUSE:
      TEST @Value(dl_need_new_column_name) = true
      TEST @Value(dl_new_column_name) ATTRIBUTE_HAS_VALUE ""
    TEST_MODE = TEST
    PASSED -> AttributeCreator
AttributeCreator
    ATTR_TABLE = SET_TO column_name = @Value(dl_new_column_name)
    -> Aggregator_2
Aggregator_2
    ACCUM_ATTRS_NAME = Use Attributes From One Feature
    AGGREGATE_TYPE = Homogeneous Collection (If Possible)
    COUNT_ATTR = AntalSameColumns
    GROUP_BY = fme_feature_type_name dl_new_column_name
    MODE = Geometry - Assemble One Level
    ORDERED = No
    SEP = ,
    AGGREGATE -> Tester_3
Tester_3
    BOOL_OP = OR
    TEST_CLAUSE = TEST @Value(AntalSameColumns) > 1
    TEST_MODE = TEST
    PASSED -> Aggregator_4

Bookmark: För loggning
FeatureMerger_6
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_5

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    INCLUDE_OFFSET = NO
    STAMP_TYPE = datetime
    TIMEZONE = local
    -> DateTimeConverter
DateTimeConverter
    DATETIME_ATTR = _dts
    OUT_FORMAT = %Y-%m-%d %H:%M:%S
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    NO_MATCH = _FME_NO_OP_
    REGEXP = YES
    SRC_ATTRS = _dts
    -> StringReplacer_2
StringReplacer_2
    CASE = NO
    FIND_TEXT = .*\.
    NO_MATCH = _FME_NO_OP_
    REGEXP = YES
    SRC_ATTRS = _mils
    -> SubstringExtractor
SubstringExtractor
    END = 2
    RESULT_ATTR = _subMils
    SRC_STRING = @Value(_mils)
    START = 0
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)
