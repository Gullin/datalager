FME workspace 02-GSD-Fastighetskartan-DatalagerManage-old01.fmw

Parameters:
- RotDirectory = ../   # Katalogen där processen startar
- ProcessName =   # Processnamn
- OutputDirectory = ../   # Katalog för lagring av del av datalager
- InData = C:\Dev\Datalager_procsrc\lm-geodataplatsen-fastighetskartan\_ned\fk_12.Sweref_99_TM.Shape.zip   # Indata (shape eller zip)
- FEATURE_TYPES =
- SourceCutSurface = $(FME_MF_DIR_USERTYPED)KlippytorSweref9913030.ffs   # Källa klippytor

Readers:
- FFS_1: FFS from $(SourceCutSurface)
- ESRISHAPE_1: ESRISHAPE from $(InData)

Writers:
- ESRISHAPE_2: ESRISHAPE to $(OutputDirectory)
- SDF3_1: SDF3 to $(OutputDirectory)

Bookmark: Klippning och transformering
ak_12 (reader ESRISHAPE_1)
    attributes: DETALJTYP char(10), ADAT char(16), LANKOD char(2), KOMMUNKOD char(4), KOMMUNNAMN char(16), OMRNR short, OMRTYP char(30), FNR_FDS char(9), EXTERNID char(64), YTKVAL short, BLOCKENHET char(9), FASTIGHET char(54), TRAKT char(40), _clipped char(200)
    -> Junction_3
Note: Junction_14 : Input
Junction_3
    -> Junction_5
Note: <All>
Junction_5
    -> ClippReprojectMulti [Cleepe]
Klippytor (reader FFS_1)
    attributes: Namn varchar(200)
    -> ParameterFetcher
ParameterFetcher
    ATTR_LIST = ProcessName $(ProcessName) RotDirectory $(RotDirectory) ShpInData $(InData)
    -> UUIDGenerator
UUIDGenerator
    UUID_ATTR = ProcessID
    -> Junction
    -> Sampler_2
    -> Sampler_3
Note: ClippReprojectMulti : Clipper
Junction
    -> Junction_2
Note: UUIDGenerator : Output
Junction_2
    -> ClippReprojectMulti [Clipper]
ClippReprojectMulti: Klipp och transformera
    PROCESSNAME = @Value(ProcessName)
    NAMN = @Value(Namn)
    ROTDIRECTORY = @Value(RotDirectory)
    FME_BASENAME = @Value(fme_basename)
    PROCESSID = @Value(ProcessID)
    Inside -> Shapefile1 (writer ESRISHAPE_2)
    Inside -> FeatureClass1 (writer SDF3_1)
Shapefile1 (writer ESRISHAPE_2)
FeatureClass1 (writer SDF3_1)

Bookmark: Loggning
Note: Endast till för som signal att starta logg
Sampler_2
    SAMPLE_TYPE_LONG = First N Features
    RATE = 1
    SAMPLE_MODE = No
    SAMPLED -> StringConcatenator_2
StringConcatenator_2
    ACTION = Create New Attribute
    VAL_ATTR = Logg
    PARM_LINE = Kör @Value(ProcessName) för data "@Value(ShpInData)" till datalagret.
    -> TimeStamper_2
TimeStamper_2
    FMT = ^Y-^m-^d ^H:^M:^S
    TIME_ATTR = Timestamp
    -> Logg_2
Logg_2: WorkspaceRunner
    WORKSPACE_FILE = C:\Dev\Datalager_procsrc\_sys\_logg.fmw
    WORKSPACE_PARAMETERS = EX_DATE_TIME,@Value(Timestamp),EX_PROCESS_NAME,@Value(ProcessName),EX_ID,@Value(ProcessID),EX_TYPE,INFORMATION,EX,@Value(Logg),EX_WorkSpace,$(FME_MF_DIR_USERTYPED)$(FME_MF_NAME),EX_ROT_DIRECTORY,@Value(RotDirectory)
    BLOCKING = No
Note: Loggar när processen är färdigkörd.
Sampler_3
    SAMPLE_TYPE_LONG = First N Features
    RATE = 1
    SAMPLE_MODE = No
    SAMPLED -> StringConcatenator_6
StringConcatenator_6
    ACTION = Create New Attribute
    VAL_ATTR = Logg
    PARM_LINE = Kör @Value(ProcessName) för data "@Value(ShpInData)" till datalagret.
    -> Logg_6
Note: Tidsstämpel lämnas tom för att logga loggningsrutinen skapa tiden. / Ska vänta till processen är helt färdig.
Logg_6: WorkspaceRunner
    WORKSPACE_FILE = C:\Dev\Datalager_procsrc\_sys\_logg.fmw
    WORKSPACE_PARAMETERS = EX_DATE_TIME,,EX_PROCESS_NAME,@Value(ProcessName),EX_ID,@Value(ProcessID),EX_TYPE,KLART,EX,@Value(Logg),EX_WorkSpace,$(FME_MF_DIR_USERTYPED)$(FME_MF_NAME),EX_ROT_DIRECTORY,@Value(RotDirectory)
    BLOCKING = Yes

FME custom transformer Klipp och transformera
Klipper efter Landskronas behov av indelning.
Transformerar från SWEREF 99 TM till SWEREF 99 13 30.
Utdata är data inom klippytan uppmärkt via attribut broende av indelning.

Parameters:
- PROCESSID = @Value(ProcessID)   # ProcessID
- PROCESSNAME = @Value(ProcessName)   # ProcessName
- ROTDIRECTORY = @Value(RotDirectory)   # RotDirectory
- FME_BASENAME = @Value(fme_basename)   # Fme Basename
- NAMN = @Value(Namn)   # Namn

Clipper (input)
    -> TestFilter
TestFilter
    TEST_LIST = BOOL_OP,OR,COMPOSITE_TEST,<Unused>,TEST_CLAUSE,"TEST @Value(Namn) = Landskrona",Landskrona,BOOL_OP,OR,COMPOSITE_TEST,<Unused>,TEST_CLAUSE,"TEST @Value(Namn) = Krans",Kranskommuner,BOOL_OP,OR,COMPOSITE_TEST,<Unused>,TEST_CLAUSE,"TEST @Value(Namn) = LandskronaKrans",Landskrona med kranskommuner,BOOL_OP,OR,COMPOSITE_TEST,<Unused>,TEST_CLAUSE,"TEST @Value(Namn) = Skane",Skåne
    DEFAULT_VALUE = <UNFILTERED>
    Landskrona -> Clipper_Landskrona [CLIPPER]
    Kranskommuner -> Clipper_Krans [CLIPPER]
    Landskrona med kranskommuner -> Clipper_Landskrona_Krans [CLIPPER]
    Skåne -> Clipper_Skåne [CLIPPER]
    <UNFILTERED> -> Aggregator
Cleepe (input)
    -> GtransReprojector
Note: GtransReprojector [GtransReprojector] / Parameters: / Translation File: C:\Program Files\FME 2017.0 (17259)\Reproject\Gtrans\Sys\SW99TM-1330.tf / Raster Parameters: / Reverse Translation File: <not set> / Interpolation Type: Nearest Neighbor / Cell Size: Square Cells
GtransReprojector
    TRANSLATION_FILE = $(FME_HOME)Reproject\Gtrans\Sys\SW99TM-1330.tf
    INTERPOLATION_TYPE_NAME = Nearest Neighbor
    RASTER_CELL_SIZE = Square Cells
    REPROJECTED -> TestFilter_2
TestFilter_2
    TEST_LIST:
      BOOL_OP,OR,COMPOSITE_TEST,<Unused>,TEST_CLAUSE,"TEST @Value(fme_basename) BEGINS_WITH a",Fastighet,BOOL_OP,OR,COMPOSITE_TEST,<Unused>,TEST_CLAUSE,"TEST @Value(fme_basename) BEGINS_WITH b",Bebyggelse,BOOL_OP,OR,COMPOSITE_TEST,<Unused>,TEST_CLAUSE,"TEST @Value(fme_basename) BEGINS_WITH j
      TEST @Value(fme_basename) BEGINS_WITH k
      TEST @Value(fme_basename) BEGINS_WITH v",Kommunikation,BOOL_OP,OR,COMPOSITE_TEST,<Unused>,TEST_CLAUSE,"TEST @Value(fme_basename) BEGINS_WITH m",Markdata,BOOL_OP,OR,COMPOSITE_TEST,<Unused>,TEST_CLAUSE,"TEST @Value(fme_basename) BEGINS_WITH h",Hydrografi,BOOL_OP,OR,COMPOSITE_TEST,<Unused>,TEST_CLAUSE,"TEST @Value(fme_basename) BEGINS_WITH r",Rättigheter och GA,BOOL_OP,OR,COMPOSITE_TEST,<Unused>,TEST_CLAUSE,"TEST @Value(fme_basename) BEGINS_WITH p",Planer,BOOL_OP,OR,COMPOSITE_TEST,<Unused>,TEST_CLAUSE,"TEST @Value(fme_basename) BEGINS_WITH e",Bestämmelser,BOOL_OP,OR,COMPOSITE_TEST,<Unused>,TEST_CLAUSE,"TEST @Value(fme_basename) BEGINS_WITH l",Fornlämningar,BOOL_OP,OR,COMPOSITE_TEST,<Unused>,TEST_CLAUSE,"TEST @Value(fme_basename) BEGINS_WITH o",Höjdkurvor,BOOL_OP,OR,COMPOSITE_TEST,<Unused>,TEST_CLAUSE,"TEST @Value(fme_basename) BEGINS_WITH f
      TEST @Value(fme_basename) BEGINS_WITH n
      TEST @Value(fme_basename) BEGINS_WITH q
      TEST @Value(fme_basename) BEGINS_WITH t",Övrigt
    DEFAULT_VALUE = <UNFILTERED>
    Fastighet -> AttributeCreator
    Bebyggelse -> AttributeCreator_2
    Kommunikation -> AttributeCreator_3
    Markdata -> AttributeCreator_4
    Hydrografi -> AttributeCreator_5
    Rättigheter och GA -> AttributeCreator_6
    Planer -> AttributeCreator_7
    Bestämmelser -> AttributeCreator_8
    Fornlämningar -> AttributeCreator_9
    Höjdkurvor -> AttributeCreator_10
    Övrigt -> AttributeCreator_11
AttributeCreator
    ATTR_TABLE = SET_TO Tema = Fastighetsindelning
    -> AttributeCreator_OUTPUT
AttributeCreator_2
    ATTR_TABLE = SET_TO Tema = Bebyggelse
    -> AttributeCreator_OUTPUT
AttributeCreator_3
    ATTR_TABLE = SET_TO Tema = Kommunikation
    -> AttributeCreator_OUTPUT
AttributeCreator_4
    ATTR_TABLE = SET_TO Tema = Markdata
    -> AttributeCreator_OUTPUT
AttributeCreator_5
    ATTR_TABLE = SET_TO Tema = Hydrografi
    -> AttributeCreator_OUTPUT
AttributeCreator_6
    ATTR_TABLE = SET_TO Tema = Rattigheter_gemensamhetsanlaggningar
    -> AttributeCreator_OUTPUT
AttributeCreator_7
    ATTR_TABLE = SET_TO Tema = Planer
    -> AttributeCreator_OUTPUT
AttributeCreator_8
    ATTR_TABLE = SET_TO Tema = Bestammelser
    -> AttributeCreator_OUTPUT
AttributeCreator_9
    ATTR_TABLE = SET_TO Tema = Fornlamningar
    -> AttributeCreator_OUTPUT
AttributeCreator_10
    ATTR_TABLE = SET_TO Tema = Hojdkurvor
    -> AttributeCreator_OUTPUT
AttributeCreator_11
    ATTR_TABLE = SET_TO Tema = Ovrigt
    -> AttributeCreator_OUTPUT
AttributeCreator_OUTPUT: Junction
    -> Clipper_Skåne [CLIPPEE]
Clipper_Skåne
    CLIPPER_PREFIX = Clipper
    MISSING_VAL_MODE = Compute
    CREATE_AGGREGATES = Yes
    PRESERVE_CLIPPEE_EXTENTS = No
    BOUNDARY_CASES = Treat as Inside
    CLIPPED_ATTR = _clipped
    CLIP_TYPE = Multiple Clippers
    VAL_SOURCE = Clippee Only
    LINES_AS_SEGMENTS = No
    ATTR_ACCUM_MODE = Prefix Clipper
    MEASURE_TYPE = Continuous
    INSIDE -> Inside (output)
    INSIDE -> Clipper_Landskrona_Krans [CLIPPEE]
    <REJECTED> -> Aggregator_2
Clipper_Landskrona_Krans
    CLIPPER_PREFIX = Clipper
    MISSING_VAL_MODE = Compute
    CREATE_AGGREGATES = Yes
    PRESERVE_CLIPPEE_EXTENTS = No
    BOUNDARY_CASES = Treat as Inside
    CLIPPED_ATTR = _clipped
    CLIP_TYPE = Multiple Clippers
    VAL_SOURCE = Clippee Only
    LINES_AS_SEGMENTS = No
    ATTR_ACCUM_MODE = Prefix Clipper
    MEASURE_TYPE = Continuous
    INSIDE -> Inside (output)
    INSIDE -> Clipper_Krans [CLIPPEE]
    INSIDE -> Clipper_Landskrona [CLIPPEE]
    <REJECTED> -> Aggregator_3
Clipper_Landskrona
    CLIPPER_PREFIX = Clipper
    MISSING_VAL_MODE = Compute
    CREATE_AGGREGATES = Yes
    PRESERVE_CLIPPEE_EXTENTS = No
    BOUNDARY_CASES = Treat as Inside
    CLIPPED_ATTR = _clipped
    CLIP_TYPE = Multiple Clippers
    VAL_SOURCE = Clippee Only
    LINES_AS_SEGMENTS = No
    ATTR_ACCUM_MODE = Prefix Clipper
    MEASURE_TYPE = Continuous
    INSIDE -> Inside (output)
    <REJECTED> -> Aggregator_5
Clipper_Krans
    CLIPPER_PREFIX = Clipper
    MISSING_VAL_MODE = Compute
    CREATE_AGGREGATES = Yes
    PRESERVE_CLIPPEE_EXTENTS = No
    BOUNDARY_CASES = Treat as Inside
    CLIPPED_ATTR = _clipped
    CLIP_TYPE = Multiple Clippers
    VAL_SOURCE = Clippee Only
    LINES_AS_SEGMENTS = No
    ATTR_ACCUM_MODE = Prefix Clipper
    MEASURE_TYPE = Continuous
    INSIDE -> Inside (output)
    <REJECTED> -> Aggregator_4
Inside (output)

Bookmark: Loggning
Aggregator
    CONCAT_ATTRS = Namn
    ACCUM_ATTRS_NAME = Use Attributes From One Feature
    COUNT_ATTR = Antal
    AGGREGATE_TYPE = Homogeneous Collection (If Possible)
    MODE = Geometry - Assemble One Level
    SEP = ", "
    ORDERED = No
    AGGREGATE -> StringConcatenator
StringConcatenator
    ACTION = Create New Attribute
    VAL_ATTR = Logg
    PARM_LINE = Klippytorna (@Value(Antal) st.) @Value(Namn) används ej.
    -> TimeStamper
TimeStamper
    FMT = ^Y-^m-^d ^H:^M:^S
    TIME_ATTR = Timestamp
    -> Logg_01
Logg_01: WorkspaceRunner
    WORKSPACE_FILE = C:\Dev\Datalager_procsrc\_sys\_logg.fmw
    WORKSPACE_PARAMETERS = EX_DATE_TIME,@Value(Timestamp),EX_PROCESS_NAME,@Value(ProcessName),EX_ID,@Value(ProcessID),EX_TYPE,INFORMATION,EX,@Value(Logg),EX_WorkSpace,$(FME_MF_DIR_USERTYPED)$(FME_MF_NAME),EX_ROT_DIRECTORY,@Value(RotDirectory)
    BLOCKING = No
Aggregator_5
    CONCAT_ATTRS = fme_rejection_code
    ACCUM_ATTRS_NAME = Use Attributes From One Feature
    COUNT_ATTR = Antal
    AGGREGATE_TYPE = Homogeneous Collection (If Possible)
    MODE = Geometry - Assemble One Level
    SEP = ", "
    ORDERED = No
    AGGREGATE -> StringConcatenator_5
StringConcatenator_5
    ACTION = Create New Attribute
    VAL_ATTR = Logg
    PARM_LINE = Vid klippningen @Value(Namn) uppstår @Value(Antal) st. ogiltiga klippytor och objekt med förkastningskoden @Value(fme_rejection_code).
    -> TimeStamper_5
TimeStamper_5
    FMT = ^Y-^m-^d ^H:^M:^S
    TIME_ATTR = Timestamp
    -> Logg_5
Logg_5: WorkspaceRunner
    WORKSPACE_FILE = C:\Dev\Datalager_procsrc\_sys\_logg.fmw
    WORKSPACE_PARAMETERS = EX_DATE_TIME,@Value(Timestamp),EX_PROCESS_NAME,@Value(ProcessName),EX_ID,@Value(ProcessID),EX_TYPE,VARNING,EX,@Value(Logg),EX_WorkSpace,$(FME_MF_DIR_USERTYPED)$(FME_MF_NAME),EX_ROT_DIRECTORY,@Value(RotDirectory)
    BLOCKING = No
Aggregator_4
    CONCAT_ATTRS = fme_rejection_code
    ACCUM_ATTRS_NAME = Use Attributes From One Feature
    COUNT_ATTR = Antal
    AGGREGATE_TYPE = Homogeneous Collection (If Possible)
    MODE = Geometry - Assemble One Level
    SEP = ", "
    ORDERED = No
    AGGREGATE -> StringConcatenator_4
StringConcatenator_4
    ACTION = Create New Attribute
    VAL_ATTR = Logg
    PARM_LINE = Vid klippningen @Value(Namn) uppstår @Value(Antal) st. ogiltiga klippytor och objekt med förkastningskoden @Value(fme_rejection_code).
    -> TimeStamper_4
TimeStamper_4
    FMT = ^Y-^m-^d ^H:^M:^S
    TIME_ATTR = Timestamp
    -> Logg_4
Logg_4: WorkspaceRunner
    WORKSPACE_FILE = C:\Dev\Datalager_procsrc\_sys\_logg.fmw
    WORKSPACE_PARAMETERS = EX_DATE_TIME,@Value(Timestamp),EX_PROCESS_NAME,@Value(ProcessName),EX_ID,@Value(ProcessID),EX_TYPE,VARNING,EX,@Value(Logg),EX_WorkSpace,$(FME_MF_DIR_USERTYPED)$(FME_MF_NAME),EX_ROT_DIRECTORY,@Value(RotDirectory)
    BLOCKING = No
Aggregator_3
    CONCAT_ATTRS = fme_rejection_code
    ACCUM_ATTRS_NAME = Use Attributes From One Feature
    COUNT_ATTR = Antal
    AGGREGATE_TYPE = Homogeneous Collection (If Possible)
    MODE = Geometry - Assemble One Level
    SEP = ", "
    ORDERED = No
    AGGREGATE -> StringConcatenator_3
StringConcatenator_3
    ACTION = Create New Attribute
    VAL_ATTR = Logg
    PARM_LINE = Vid klippningen @Value(Namn) uppstår @Value(Antal) st. ogiltiga klippytor och objekt med förkastningskoden @Value(fme_rejection_code).
    -> TimeStamper_3
TimeStamper_3
    FMT = ^Y-^m-^d ^H:^M:^S
    TIME_ATTR = Timestamp
    -> Logg_3
Logg_3: WorkspaceRunner
    WORKSPACE_FILE = C:\Dev\Datalager_procsrc\_sys\_logg.fmw
    WORKSPACE_PARAMETERS = EX_DATE_TIME,@Value(Timestamp),EX_PROCESS_NAME,@Value(ProcessName),EX_ID,@Value(ProcessID),EX_TYPE,VARNING,EX,@Value(Logg),EX_WorkSpace,$(FME_MF_DIR_USERTYPED)$(FME_MF_NAME),EX_ROT_DIRECTORY,@Value(RotDirectory)
    BLOCKING = No
Aggregator_2
    CONCAT_ATTRS = fme_rejection_code
    ACCUM_ATTRS_NAME = Use Attributes From One Feature
    COUNT_ATTR = Antal
    AGGREGATE_TYPE = Homogeneous Collection (If Possible)
    MODE = Geometry - Assemble One Level
    SEP = ", "
    ORDERED = No
    AGGREGATE -> StringConcatenator_2
StringConcatenator_2
    ACTION = Create New Attribute
    VAL_ATTR = Logg
    PARM_LINE = Vid klippningen @Value(Namn) uppstår @Value(Antal) st. ogiltiga klippytor och objekt med förkastningskoden @Value(fme_rejection_code).
    -> TimeStamper_2
TimeStamper_2
    FMT = ^Y-^m-^d ^H:^M:^S
    TIME_ATTR = Timestamp
    -> Logg_2
Logg_2: WorkspaceRunner
    WORKSPACE_FILE = C:\Dev\Datalager_procsrc\_sys\_logg.fmw
    WORKSPACE_PARAMETERS = EX_DATE_TIME,@Value(Timestamp),EX_PROCESS_NAME,@Value(ProcessName),EX_ID,@Value(ProcessID),EX_TYPE,VARNING,EX,@Value(Logg),EX_WorkSpace,$(FME_MF_DIR_USERTYPED)$(FME_MF_NAME),EX_ROT_DIRECTORY,@Value(RotDirectory)
    BLOCKING = No
