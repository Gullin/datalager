FME workspace 01-KlippytorFromFKSkaneSw99TM.fmw

Parameters:
- RotDirectory = ../   # Katalogen där processen startar
- ProcessName = TestKlippytor   # Processnamn
- ShpInData = C:\Dev\Datalager\lm-geodataplatsen-fastighetskartan\_ned\fk_12.Sweref_99_TM.Shape.zip   # Indata (shape eller zip)
- Buffer = 5   # Buffertavstånd från kommungränser
- ProcessModulName =   # Processmodulsnamn
- IsWholeProcessRun = 1   # Är hela datalagerprocessen körd
- OutputDirectory = $(RotDirectory)$(ProcessModulName)/_temp/KlippytorSweref991330.ffs   # Destination FME Feature Store (FFS) Fil

Readers:
- ESRISHAPE_1: ESRISHAPE from $(ShpInData)

Writers:
- FFS_1: FFS to $(OutputDirectory)

Note: Parametrar / * [RotDirectory] Kommer från batch-processen och är obligatoriskt för alla FME-processor. / * [ProcessName] Kommer från batch-processen och är obligatoriskt för alla FME-processor. / * [ShpInData] Sökvägen till var zip-filen med data ligger (dataschema enligt "ak_12"). / * [Buffer] Buffertavstånd till klippytorna i meter. Valfri. Standard 5 m om inget väljs. / * [OutputDirectory] Klippytorna lagras. Sätts av processen och som standard katalogen FME-processen är sparad i. / Data behöver vara hemtaget sedan tidigare i en annan process.
ak_12 (reader ESRISHAPE_1)
    attributes: DETALJTYP char(10), ADAT char(16), LANKOD char(2), KOMMUNKOD char(4), KOMMUNNAMN char(16)
    -> ParameterFetcher
ParameterFetcher
    ATTR_LIST = _Buffer $(Buffer) _ProcessName $(ProcessName) _ShpInData $(ShpInData) _RotDirectory $(RotDirectory)
    -> UUIDGenerator_2
UUIDGenerator_2
    UUID_ATTR = ProcessID
    -> TestFilter
    -> Sampler
TestFilter
    DEFAULT_VALUE = <UNFILTERED>
    TEST_LIST = BOOL_OP,OR,COMPOSITE_TEST,<Unused>,TEST_CLAUSE,"TEST @Value(KOMMUNKOD) = 1282",1282 Landskrona,BOOL_OP,OR,COMPOSITE_TEST,<Unused>,TEST_CLAUSE,"TEST @Value(KOMMUNKOD) = 1283",1283 Helsingborg,BOOL_OP,OR,COMPOSITE_TEST,<Unused>,TEST_CLAUSE,"TEST @Value(KOMMUNKOD) = 1214",1214 Svalöv,BOOL_OP,OR,COMPOSITE_TEST,<Unused>,TEST_CLAUSE,"TEST @Value(KOMMUNKOD) = 1261",1261 Kävlinge
    1282 Landskrona -> Bufferer_lkr
    1282 Landskrona -> Aggregator_lkrkrans
    1282 Landskrona -> Aggregator_skane
    1283 Helsingborg -> Aggregator_krans
    1283 Helsingborg -> Aggregator_lkrkrans
    1283 Helsingborg -> Aggregator_skane
    1214 Svalöv -> Aggregator_krans
    1214 Svalöv -> Aggregator_lkrkrans
    1214 Svalöv -> Aggregator_skane
    1261 Kävlinge -> Aggregator_krans
    1261 Kävlinge -> Aggregator_lkrkrans
    1261 Kävlinge -> Aggregator_skane
    <UNFILTERED> -> Aggregator_skane
Bufferer_lkr
    INTERP_SEGMENTS = 8
    CAP_STYLE = Round
    OFFSET = @Value(_Buffer)
    BUFFERED -> AttributeCreator_2
AttributeCreator_2
    ATTR_LIST = Namn,Landskrona
    -> GtransReprojector
Aggregator_lkrkrans
    ACCUM_ATTRS_NAME = Yes
    AGGREGATE_TYPE = Homogeneous Collection (If Possible)
    MODE = Geometry - Assemble One Level
    SEP = ,
    ORDERED = No
    AGGREGATE -> Dissolver_lkrkrans
Dissolver_lkrkrans
    NO_OVRLP = No
    ACCUM_INPUT_ATTRS = Yes
    AREA -> Bufferer_lkrkrans
    <REJECTED> -> Sampler_3
Bufferer_lkrkrans
    INTERP_SEGMENTS = 8
    CAP_STYLE = Round
    OFFSET = @Value(_Buffer)
    BUFFERED -> AttributeCreator_3
AttributeCreator_3
    ATTR_LIST = Namn,LandskronaKrans
    -> GtransReprojector
Aggregator_krans
    ACCUM_ATTRS_NAME = Yes
    AGGREGATE_TYPE = Homogeneous Collection (If Possible)
    MODE = Geometry - Assemble One Level
    SEP = ,
    ORDERED = No
    AGGREGATE -> Dissolver_krans
Dissolver_krans
    NO_OVRLP = No
    ACCUM_INPUT_ATTRS = Yes
    AREA -> Bufferer_krans
    <REJECTED> -> Sampler_4
Bufferer_krans
    INTERP_SEGMENTS = 8
    CAP_STYLE = Round
    OFFSET = @Value(_Buffer)
    BUFFERED -> AttributeCreator_4
AttributeCreator_4
    ATTR_LIST = Namn,Krans
    -> GtransReprojector
Aggregator_skane
    ACCUM_ATTRS_NAME = Yes
    AGGREGATE_TYPE = Homogeneous Collection (If Possible)
    MODE = Geometry - Assemble One Level
    SEP = ,
    ORDERED = No
    AGGREGATE -> Dissolver_skane
Dissolver_skane
    NO_OVRLP = No
    ACCUM_INPUT_ATTRS = Yes
    AREA -> Bufferer_skane
    <REJECTED> -> Sampler_5
Bufferer_skane
    INTERP_SEGMENTS = 8
    CAP_STYLE = Round
    OFFSET = @Value(_Buffer)
    BUFFERED -> AttributeCreator_5
AttributeCreator_5
    ATTR_LIST = Namn,Skane
    -> GtransReprojector
GtransReprojector
    INTERPOLATION_TYPE_NAME = Nearest Neighbor
    RASTER_CELL_SIZE = Square Cells
    TRANSLATION_FILE = $(FME_HOME)Reproject\Gtrans\Sys\SW99TM-1330.tf
    REPROJECTED -> AttributeRemover
    REPROJECTED -> Sampler_2
AttributeRemover
    REMOVE_ATTRS = _ShpInData,KOMMUNNAMN,LANKOD,DETALJTYP,ADAT,KOMMUNKOD,_Buffer,_RotDirectory,_ProcessName,ProcessID
    -> Klippytor (writer FFS_1)
Klippytor (writer FFS_1)
    attributes: Namn varchar(200)

Bookmark: Loggning
Note: Endast till för att logga felet
Sampler_3
    RATE = 1
    SAMPLE_TYPE_LONG = First N Features
    SAMPLE_MODE = No
    SAMPLED -> StringConcatenator_2
StringConcatenator_2
    ACTION = Create New Attribute
    PARM_LINE = Inga polygoner att slå ihop (dissolve) för Landskrona och dess kranskommuner.
    VAL_ATTR = Logg
    -> DTStamperYYYY-MM-DD_HH:MI:SS.sss_2
DTStamperYYYY-MM-DD_HH:MI:SS.sss_2
    -> Logg_02
Logg_02: WorkspaceRunner
    WORKSPACE_PARAMETERS = EX_DATE_TIME,@Value(_datetimestamp),EX_PROCESS_NAME,@Value(_ProcessName),EX_ID,@Value(ProcessID),EX_TYPE,ERROR,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
    BLOCKING = Yes
    WORKSPACE_FILE = C:\dev\Datalager_procsrc\_sys\_logg.fmw
Note: Endast till för att logga felet
Sampler_4
    RATE = 1
    SAMPLE_TYPE_LONG = First N Features
    SAMPLE_MODE = No
    SAMPLED -> StringConcatenator_3
StringConcatenator_3
    ACTION = Create New Attribute
    PARM_LINE = Inga polygoner att slå ihop (dissolve) för Landskrona kranskommuner.
    VAL_ATTR = Logg
    -> DTStamperYYYY-MM-DD_HH:MI:SS.sss_3
DTStamperYYYY-MM-DD_HH:MI:SS.sss_3
    -> Logg_03
Logg_03: WorkspaceRunner
    WORKSPACE_PARAMETERS = EX_DATE_TIME,@Value(_datetimestamp),EX_PROCESS_NAME,@Value(_ProcessName),EX_ID,@Value(ProcessID),EX_TYPE,ERROR,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
    BLOCKING = Yes
    WORKSPACE_FILE = C:\dev\Datalager_procsrc\_sys\_logg.fmw
Note: Endast till för som signal att markera klart i logg
Sampler_2
    RATE = 1
    SAMPLE_TYPE_LONG = First N Features
    SAMPLE_MODE = No
    SAMPLED -> StringConcatenator_5
StringConcatenator_5
    ACTION = Create New Attribute
    PARM_LINE = Klippytor skapade
    VAL_ATTR = Logg
    -> DTStamperYYYY-MM-DD_HH:MI:SS.sss_5
DTStamperYYYY-MM-DD_HH:MI:SS.sss_5
    -> Logg_05
Logg_05: WorkspaceRunner
    WORKSPACE_PARAMETERS = EX_DATE_TIME,@Value(_datetimestamp),EX_PROCESS_NAME,@Value(_ProcessName),EX_ID,@Value(ProcessID),EX_TYPE,KLART,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
    BLOCKING = Yes
    WORKSPACE_FILE = C:\dev\Datalager_procsrc\_sys\_logg.fmw
Note: Endast till för att logga felet
Sampler_5
    RATE = 1
    SAMPLE_TYPE_LONG = First N Features
    SAMPLE_MODE = No
    SAMPLED -> StringConcatenator_4
StringConcatenator_4
    ACTION = Create New Attribute
    PARM_LINE = Inga polygoner att slå ihop (dissolve) för Skåne.
    VAL_ATTR = Logg
    -> DTStamperYYYY-MM-DD_HH:MI:SS.sss_4
DTStamperYYYY-MM-DD_HH:MI:SS.sss_4
    -> Logg_04
Logg_04: WorkspaceRunner
    WORKSPACE_PARAMETERS = EX_DATE_TIME,@Value(_datetimestamp),EX_PROCESS_NAME,@Value(_ProcessName),EX_ID,@Value(ProcessID),EX_TYPE,ERROR,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
    BLOCKING = Yes
    WORKSPACE_FILE = C:\dev\Datalager_procsrc\_sys\_logg.fmw
Note: Endast till för som signal att starta logg
Sampler
    RATE = 1
    SAMPLE_TYPE_LONG = First N Features
    SAMPLE_MODE = No
    SAMPLED -> StringConcatenator
StringConcatenator
    ACTION = Create New Attribute
    PARM_LINE = Skapar klippytor av "@Value(_ShpInData)" med @Value(_Buffer) m buffert.
    VAL_ATTR = Logg
    -> DTStamperYYYY-MM-DD_HH:MI:SS.sss
DTStamperYYYY-MM-DD_HH:MI:SS.sss
    -> Logg_01
Logg_01: WorkspaceRunner
    WORKSPACE_PARAMETERS = EX_DATE_TIME,@Value(_datetimestamp),EX_PROCESS_NAME,@Value(_ProcessName),EX_ID,@Value(ProcessID),EX_TYPE,INFORMATION,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
    BLOCKING = No
    WORKSPACE_FILE = C:\dev\Datalager_procsrc\_sys\_logg.fmw

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    TIMEZONE = local
    INCLUDE_OFFSET = NO
    DATETIME_ATTR = _dts
    STAMP_TYPE = datetime
    -> DateTimeConverter
DateTimeConverter
    REPAIR_INPUT = NO
    DATETIME_ATTR = _dts
    OUT_FORMAT = %Y-%m-%d %H:%M:%S
    -> AttributeCreator
    <REJECTED> -> <Rejected> (output)
AttributeCreator
    ATTR_TABLE = SET_TO _mils = @Value(_dts)
    -> StringReplacer
StringReplacer
    REGEXP = YES
    FIND_TEXT = \.\d*
    NO_MATCH = _FME_NO_OP_
    CASE = NO
    SRC_ATTRS = _dts
    -> StringReplacer_2
StringReplacer_2
    REGEXP = YES
    FIND_TEXT = .*\.
    NO_MATCH = _FME_NO_OP_
    CASE = NO
    SRC_ATTRS = _mils
    -> SubstringExtractor
SubstringExtractor
    START = 0
    RESULT_ATTR = _subMils
    SRC_STRING = @Value(_mils)
    END = 2
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)
