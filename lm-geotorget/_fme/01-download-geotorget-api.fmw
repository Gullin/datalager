FME workspace 01-download-geotorget-api.fmw

Parameters:
- RotDirectory = ../   # Katalogen där processen startar
- OnlyOrder = 0   # Lägger endast ny beställning av leverans på befintliga ordrar (värde 1)
- ProcessName =   # Processnamn
- OutputDirectory = ../   # Katalog för lagring av nedladdat
- ProcessModulName =   # Processmodulsnamn
- IsWholeProcessRun = 1   # Är hela datalagerprocessen körd
- FME_USER_PARAM_PRIVATE_GRP =   # Private Parameters
- FeatureListFile = _modul-settings-datasets.ini   # Fil med listade features
- GeotorgetOrderID =   # Lantmäteriets Geotorgets order-ID
- MaxTimmarTillNyLeverans = 168   # Max tid för beställning av ny leverans (h)
- CONSUMERKEY =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   # Consumer Key
- CONSUMERSECRET =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   # Consumer Secret
- OPTIONAL_SCOPE =   # If the application requires a scope, input the scope here

Creator
    GEOMTYPE = Geometry Object
    NUM = 1
    CREATED -> ParameterFetcher
ParameterFetcher
    ATTR_LIST = _CONSUMERKEY $(CONSUMERKEY) _CONSUMERSECRET $(CONSUMERSECRET) _ORDERID $(GeotorgetOrderID) _MAXHOURTONEWDELIVERY $(MaxTimmarTillNyLeverans) _RotDirectory $(RotDirectory) _ProcessModulName $(ProcessModulName)
    -> UUIDGenerator_2
UUIDGenerator_2
    UUID_ATTR = ProcessID
    -> FeatureReader_2 [INITIATOR]
    -> StringConcatenator_13
FeatureReader_2
    ATTR_ACCUM_MODE = Only Use Result
    COMBINE_GEOM = Use Result
    CSV2_CASE_SENSITIVE_FIELD_NAMES = Yes
    CSV2_CHUNK_SIZE = 100000
    CSV2_DATA_START_LINE = 1
    CSV2_DELIMITER = |
    CSV2_ENCODING = ibm437
    CSV2_ENFORCE_STRICT_SCHEMA = No
    CSV2_FEATURE_TYPE_NAME = FORMAT_NAME
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 1000
    CSV2_SCAN_TYPES = No
    CSV2_SKIP_DUPLICATE_DELIMITERS = No
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = NO
    DATASET = $(RotDirectory)$(ProcessName)/_schema/$(FeatureListFile)
    FORMAT = CSV2
    INTERACT = <No Spatial Filter>
    OUTPUT_FEATURES_DISPLAY = Data Features
    <OTHER> -> AttributeExposer
    INITIATOR -> FeatureMerger_4 [REQUESTOR]
AttributeExposer
    ATTR_LIST = col0,col1,col2,col3,col4
    -> FeatureMerger_4 [SUPPLIER]
FeatureMerger_4
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = 1 1 AUTO
    LIST_NAME = _dataPackages
    MERGE_TYPE = Attributes Only
    PROCESS_DUPS = YES
    REJECT_NULL_MISSING_KEYS = No
    SUPPLIERS_FIRST = No
    MERGED -> ListExploder_2
ListExploder_2
    ATTR_ACCUM_MODE = Merge List Attributes
    ATTR_CONFLICT_RES = Use List Attribute Values
    LIST_ATTR = _dataPackages{}
    ELEMENTS -> Tester_3
Note: Plockar bort kommentarer och tomma rader
Tester_3
    BOOL_OP = COMPOSITE
    COMPOSITE_TEST = "1 OR ((2 OR 3) AND (4 OR 5 OR 6) AND (7 OR 8 OR 9) AND (10 OR 11 OR 12))"
    TEST_CLAUSE:
      TEST @Value(col0) BEGINS_WITH ;
      TEST col0 ATTRIBUTE_VALUE_NULL ""
      TEST col0 ATTRIBUTE_IS_EMPTY ""
      TEST col1 ATTRIBUTE_VALUE_NULL ""
      TEST col1 ATTRIBUTE_IS_EMPTY ""
      TEST col1 ATTRIBUTE_IS_MISSING ""
      TEST col2 ATTRIBUTE_VALUE_NULL ""
      TEST col2 ATTRIBUTE_IS_EMPTY ""
      TEST col2 ATTRIBUTE_IS_MISSING ""
      TEST col3 ATTRIBUTE_VALUE_NULL ""
      TEST col3 ATTRIBUTE_IS_EMPTY ""
      TEST col3 ATTRIBUTE_IS_MISSING ""
    TEST_MODE = Automatic
    FAILED -> Aggregator_2
Note: Skapar unika / order-ID:n
Aggregator_2
    ACCUM_ATTRS_NAME = Use Attributes From One Feature
    AGGREGATE_TYPE = Homogeneous Collection (If Possible)
    GROUP_BY = _CONSUMERKEY _CONSUMERSECRET _MAXHOURTONEWDELIVERY _ORDERID _ProcessModulName _RotDirectory col1 col2 fme_feature_type ProcessID
    LIST_ATTRS_TO_INCLUDE = col0
    LIST_NAME = files
    MODE = Geometry - Assemble One Level
    SEP = ,
    AGGREGATE -> AttributeCreator_3
AttributeCreator_3
    ATTR_TABLE:
      SET_TO _col1_absolute_path
      SET_TO _col2_absolute_path
    -> StringSearcher_4
Tester
    BOOL_OP = OR
    TEST_CLAUSE = TEST col1 ATTRIBUTE_HAS_A_VALUE ""
    TEST_MODE = TEST
    PASSED -> AttributeCreator
    FAILED -> AttributeManager
AttributeCreator
    ATTR_TABLE = SET_TO _ORDERID = @Value(col1)
    -> AttributeManager
AttributeManager
    ATTR_TABLE:
      REMOVE _col2_absolute_path
      REMOVE _col1_absolute_path
      REMOVE _matched_records
      REMOVE col0
      REMOVE col1
      RENAME_SET_VALUE col2 > _TargetPath
      REMOVE col3
      REMOVE col4
    -> LantmaterietAPIAccessTokenFetcher
LantmaterietAPIAccessTokenFetcher
    API_AUTH_URL = https://apimanager.lantmateriet.se
    API_KEY = @Value(_CONSUMERKEY)
    API_SECRET = @Value(_CONSUMERSECRET)
    API_TOKEN_REVOKE_URL = /oauth2/revoke
    API_TOKEN_URL = /oauth2/token
    MINIMUM_TOKEN_LIFETIME = 300
    OPTIONAL_SCOPE = $(OPTIONAL_SCOPE)
    OutputWithToken -> LantmaterietAPIDeliveryRequestor [OrderIds]
    <Rejected> -> FeatureMerger [REQUESTOR]
LantmaterietAPIDeliveryRequestor
    API_BASE_URL = https://api.lantmateriet.se
    API_DELIVERY_URL = /geotorget/nedladdning/v1/{OrderID}/leverans/latest
    API_PLACE_ORDER_URL = /geotorget/nedladdning/v1/{OrderID}/leverans
    MAX_DELIVERY_AGE = @Value(_MAXHOURTONEWDELIVERY)
    OnlyOrder = $(OnlyOrder)
    _ACCESS_TOKEN = @Value(_access_token)
    _ORDERID = @Value(_ORDERID)
    ReadyOrPending -> Tester_4
    <Rejected> -> FeatureMerger_2 [REQUESTOR]
Tester_4
    BOOL_OP = OR
    TEST_CLAUSE = TEST $(OnlyOrder) = 1
    TEST_MODE = TEST
    PASSED -> Aggregator_3
    FAILED -> LantmaterietAPIDownloadLinkFetcher [OrderIds]
LantmaterietAPIDownloadLinkFetcher
    API_BASE_URL = https://api.lantmateriet.se
    API_DELIVERY_URL = /geotorget/nedladdning/v1/{OrderID}/leverans/latest
    API_DOWNLOAD_URL = /geotorget/nedladdning/v1/{OrderID}/leverans/latest/files
    STATUS_REQUEST_INTERVAL = 30
    _ACCESS_TOKEN = @Value(_access_token)
    _ORDERID = @Value(_orderid)
    DownloadLinks -> Tester_2
    <Rejected> -> FeatureMerger_3 [REQUESTOR]
StringConcatenator_4
    ACTION = Overwrite Existing Attributes
    ATTRLIST = __href
    PARM_LINE = fme_basicstring:21%35%14:@Value(_API_BASE_URL)/geotorget/nedladdning/v1/{OrderID}@Value(__href)
    -> StringReplacer_2
StringReplacer_2
    CASE = NO
    FIND_TEXT = {OrderID}
    NO_MATCH = _FME_NO_OP_
    REGEXP = NO
    REPLACE_TEXT = @Value(__orderid)
    SRC_ATTRS = __href
    -> HTTPCaller
HTTPCaller
    CONNECTION_TIMEOUT_LENGTH = 60
    CUSTOM_HEADERS = Authorization;Bearer @Value(__access_token)
    ERROR_ATTR = _error
    FILE_PATH_ATTR = _response_file_path
    FOLLOW_REDIRECTS = FOLLOW_WITH_GET
    HTTP_METHOD = GET
    MAX_HTTP_VERSION = HTTP_2
    MAX_TRANSFERS_IN_PROGRESS = 25
    OUTPUT_FILENAME = @Value(_TargetPath)@Value(__title)
    REDIRECT_AUTH = ORIGINAL_DOMAIN_ONLY
    SAVE_FILE = File
    SAVE_MULTI = No
    STATUS_CODE_ATTR = _http_status_code
    TARGET_URL = @Value(__href)
    TRANSFER_TIMEOUT_LENGTH = 300
    USE_COOKIES = No
    VERIFY_SSL_CERTIFICATES = Yes
    -> Tester_10
    <REJECTED> -> Aggregator_11
Tester_10
    BOOL_OP = OR
    TEST_CLAUSE = CASE_INSENSITIVE_TEST @Value(_http_status_code) BEGINS_WITH 2
    TEST_MODE = TEST
    PASSED -> Aggregator
    FAILED -> Aggregator_21

Bookmark: Absolut och relativ sökväg för col2
StringSearcher_4
    CASE = no
    REGEXP = :
    STRING_TO_SEARCH = @Value(col2)
    MATCHED -> AttributeCreator_14
    NOT_MATCHED -> Tester_14
AttributeCreator_14
    ATTR_TABLE = SET_TO _col2_absolute_path = 1
    -> Junction
Tester_14
    BOOL_OP = OR
    TEST_CLAUSE:
      TEST col2 ATTRIBUTE_VALUE_NULL ""
      TEST col2 ATTRIBUTE_IS_EMPTY ""
      TEST col2 ATTRIBUTE_IS_MISSING ""
    TEST_MODE = Automatic
    PASSED -> Junction
    FAILED -> StringConcatenator_11
StringConcatenator_11
    ACTION = Create New Attribute
    PARM_LINE = fme_basicstring:21%25%1%12:@Value(_RotDirectory)@Value(_ProcessModulName)/@Value(col2)
    VAL_ATTR = col2
    -> Junction
Junction
    -> Tester

Bookmark: Annan katalog för produktkvittot, uttag.json-fil
Tester_2
    BOOL_OP = OR
    TEST_CLAUSE = CASE_INSENSITIVE_TEST @Value(__title) NOT_ENDS_WITH .json
    TEST_MODE = TEST
    PASSED -> FeatureMerger_6 [REQUESTOR]
    PASSED -> AttributeKeeper
    FAILED -> StringConcatenator
StringConcatenator
    ACTION = Overwrite Existing Attributes
    ATTRLIST = _TargetPath
    PARM_LINE = fme_basicstring:21%25%6:@Value(_RotDirectory)@Value(_ProcessModulName)/_log/
    -> StringConcatenator_4

Bookmark: Väljer ut endast de filer listade i _modul-settings-datasets.ini
AttributeKeeper
    CREATE_BULK_MODE_FEATURES = NO
    KEEP_LIST = files{} files{}.col0
    -> Sampler
Sampler
    RATE = 1
    SAMPLE_MODE = No
    SAMPLE_TYPE_LONG = First N Features
    SAMPLED -> ListExploder
ListExploder
    ATTR_ACCUM_MODE = Merge List Attributes
    ATTR_CONFLICT_RES = Use List Attribute Values
    LIST_ATTR = files{}
    ELEMENTS -> StringReplacer
StringReplacer
    CASE = NO
    FIND_TEXT = /**/*.gpkg
    NO_MATCH = _FME_NO_OP_
    REGEXP = NO
    SRC_ATTRS = col0
    -> FeatureMerger_6 [SUPPLIER]
FeatureMerger_6
    ATTR_ACCUM_MODE = Merge Supplier
    ATTR_CONFLICT_RES = Use Requestor
    IGNORE_NULLS = No
    JOIN_KEYS = @Value(__title) @Value(col0) AUTO
    MERGE_TYPE = Attributes Only
    PROCESS_DUPS = NO
    REJECT_NULL_MISSING_KEYS = No
    SUPPLIERS_FIRST = No
    MERGED -> StringConcatenator_4

Bookmark: Loggning
Aggregator_21
    ACCUM_ATTRS_NAME = Use Attributes From One Feature
    AGGREGATE_TYPE = Homogeneous Collection (If Possible)
    GROUP_BY = _http_status_code __href __title
    MODE = Geometry - Assemble One Level
    ORDERED = No
    SEP = ", "
    AGGREGATE -> StringConcatenator_2
StringConcatenator_2
    ACTION = Create New Attribute
    PARM_LINE:
      fme_basicstring:15%25%1%5%1%15%1%14:HTTP-statuskod:@Value(_http_status_code)
      Data:
      @Value(__title)
      @Value(__href)
    VAL_ATTR = _ErrorMessage
    -> Aggregator_22
Aggregator_22
    ACCUM_ATTRS_NAME = Use Attributes From One Feature
    AGGREGATE_TYPE = Homogeneous Collection (If Possible)
    CONCAT_ATTRS = _ErrorMessage
    MODE = Geometry - Assemble One Level
    ORDERED = No
    SEP = ", "
    AGGREGATE -> FeatureMerger_13 [REQUESTOR]
Aggregator
    ACCUM_ATTRS_NAME = Use Attributes From One Feature
    AGGREGATE_TYPE = Homogeneous Collection (If Possible)
    COUNT_ATTR = Antal
    MODE = Geometry - Assemble One Level
    SEP = ,
    AGGREGATE -> FeatureMerger_5 [REQUESTOR]
Aggregator_11
    ACCUM_ATTRS_NAME = Use Attributes From One Feature
    AGGREGATE_TYPE = Homogeneous Collection (If Possible)
    GROUP_BY = fme_rejection_code _error __href __title
    MODE = Geometry - Assemble One Level
    ORDERED = No
    SEP = ", "
    AGGREGATE -> StringConcatenator_24
StringConcatenator_24
    ACTION = Create New Attribute
    PARM_LINE:
      fme_basicstring:16%26%12%14%1%1%5%1%15%1%14:(FME-rejection: @Value(fme_rejection_code), http-fel: @Value(_error))
      Data:
      @Value(__title)
      @Value(__href)
    VAL_ATTR = _ErrorMessage
    -> Aggregator_12
Aggregator_12
    ACCUM_ATTRS_NAME = Use Attributes From One Feature
    AGGREGATE_TYPE = Homogeneous Collection (If Possible)
    CONCAT_ATTRS = _ErrorMessage
    MODE = Geometry - Assemble One Level
    ORDERED = No
    SEP = ", "
    AGGREGATE -> FeatureMerger_8 [REQUESTOR]
Aggregator_3
    ACCUM_ATTRS_NAME = Use Attributes From One Feature
    AGGREGATE_TYPE = Homogeneous Collection (If Possible)
    CONCAT_ATTRS = _ORDERID
    COUNT_ATTR = Antal
    MODE = Geometry - Assemble One Level
    SEP = ", "
    AGGREGATE -> FeatureMerger_7 [REQUESTOR]
StringConcatenator_13
    ACTION = Create New Attribute
    PARM_LINE = fme_basicstring:25%9:@Value(_ProcessModulName)_DOWNLOAD
    VAL_ATTR = ProcessName_DOWNLOAD
    -> AttributeCreator_6
    -> FeatureMerger [SUPPLIER]
    -> FeatureMerger_2 [SUPPLIER]
    -> FeatureMerger_3 [SUPPLIER]
    -> FeatureMerger_13 [SUPPLIER]
    -> FeatureMerger_8 [SUPPLIER]
    -> FeatureMerger_5 [SUPPLIER]
    -> FeatureMerger_7 [SUPPLIER]
FeatureMerger_8
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_15
StringConcatenator_15
    ACTION = Create New Attribute
    PARM_LINE:
      fme_basicstring:14%1%14%1%13%1%14%1%21:Förfrågan mot:
      @Value(__href)
      misslyckades.
      Felmeddelande:
      @Value(_ErrorMessage)
    VAL_ATTR = Logg
    -> DTStamperYYYY-MM-DD_HH:MI:SS.sss_8
DTStamperYYYY-MM-DD_HH:MI:SS.sss_8
    -> Logg_9
Logg_9: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DOWNLOAD),EX_ID,@Value(ProcessID),EX_TYPE,ERROR,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
FeatureMerger_13
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_23
StringConcatenator_23
    ACTION = Create New Attribute
    PARM_LINE:
      fme_basicstring:31%1%14%1%13%1%21:Förfrågan mot nedladdningslänk:
      @Value(__href)
      misslyckades.
      @Value(_ErrorMessage)
    VAL_ATTR = Logg
    -> DTStamperYYYY-MM-DD_HH:MI:SS.sss_13
DTStamperYYYY-MM-DD_HH:MI:SS.sss_13
    -> Logg_14
Logg_14: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DOWNLOAD),EX_ID,@Value(ProcessID),EX_TYPE,ERROR,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
FeatureMerger_5
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_9
StringConcatenator_9
    ACTION = Create New Attribute
    PARM_LINE = fme_basicstring:28%14%13%19:@Value(ProcessName_DOWNLOAD) avslutad med @Value(Antal) st. nedladdningar.
    VAL_ATTR = Logg
    -> DTStamperYYYY-MM-DD_HH:MI:SS.sss_5
DTStamperYYYY-MM-DD_HH:MI:SS.sss_5
    -> Logg_6
Logg_6: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DOWNLOAD),EX_ID,@Value(ProcessID),EX_TYPE,KLART,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
FeatureMerger_7
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_3
StringConcatenator_3
    ACTION = Create New Attribute
    PARM_LINE = fme_basicstring:28%14%13%31%16%1:@Value(ProcessName_DOWNLOAD) avslutad med @Value(Antal) st. beställningar av ordrarna @Value(_ORDERID).
    VAL_ATTR = Logg
    -> DTStamperYYYY-MM-DD_HH:MI:SS.sss_6
DTStamperYYYY-MM-DD_HH:MI:SS.sss_6
    -> Logg_7
Logg_7: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DOWNLOAD),EX_ID,@Value(ProcessID),EX_TYPE,KLART,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
AttributeCreator_6
    ATTR_TABLE = SET_TO _FileToRead = $(RotDirectory)$(ProcessName)/_schema/$(FeatureListFile)
    -> StringConcatenator_5
StringConcatenator_5
    ACTION = Create New Attribute
    PARM_LINE = fme_basicstring:4%28%13%18%2:Kör @Value(ProcessName_DOWNLOAD) för data i "$(FeatureListFile)".
    VAL_ATTR = Logg
    -> DTStamperYYYY-MM-DD_HH:MI:SS.sss
DTStamperYYYY-MM-DD_HH:MI:SS.sss
    -> Logg_2
Logg_2: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DOWNLOAD),EX_ID,@Value(ProcessID),EX_TYPE,INFORMATION,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> DTStamperYYYY-MM-DD_HH:MI:SS.sss_2
DTStamperYYYY-MM-DD_HH:MI:SS.sss_2
    -> Logg_3
Logg_3: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DOWNLOAD),EX_ID,@Value(ProcessID),EX_TYPE,ERROR,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> DTStamperYYYY-MM-DD_HH:MI:SS.sss_3
DTStamperYYYY-MM-DD_HH:MI:SS.sss_3
    -> Logg_4
Logg_4: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DOWNLOAD),EX_ID,@Value(ProcessID),EX_TYPE,ERROR,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
FeatureMerger_3
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> DTStamperYYYY-MM-DD_HH:MI:SS.sss_4
DTStamperYYYY-MM-DD_HH:MI:SS.sss_4
    -> Logg_5
Logg_5: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DOWNLOAD),EX_ID,@Value(ProcessID),EX_TYPE,ERROR,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)

FME custom transformer LantmaterietAPIAccessTokenFetcher
LantmaterietAPIAccessTokenFetcher
Generates an Access Token for API:s from Lantmäteriet, the Swedish mapping, cadastral and land registration authority.
If the token received expires too soon, it is revoked and a new token is generated.
This transformer can be used on its own to generate authentication for Lantmäteriet's API:s.
It can also be used together with the following transformers to handle downloads from the "Geotorget-Order - v2" API:
LantmaterietAPIDeliveryRequestor
LantmaterietAPIDownloadLinkFetcher
Create an Application, subscribe to the relevant API:s and generate keys for your application at:
https://apimanager.lantmateriet.se/store/
Input the application's Consumer Key and Consumer Secret as parameters.
Parameters
API_KEY
"Consumer Key" from the Application at https://apimanager.lantmateriet.se/store.
API_SECRET
"Consumer Secret" from the Application at https://apimanager.lantmateriet.se/store.
OPTIONAL_SCOPE
A single application may generate tokens for multiple scopes (e g for multiple clients). Tokens generated for a specific scope must be used along with their scopes in further requests.
API_BASE_URL
The base URL for the API endpoints, e g https://api.lantmateriet.se
API_TOKEN_URL
The API's token generation endpoint (excluding the base URL)
API_TOKEN_REVOKE_URL
The API's endpoint for revoking tokens (excluding the base URL)
MINIMUM_TOKEN_LIFETIME
Tokens with expires_in less than this number will be revoked and a new token is generated.
License
MIT License
Copyright © 2021, Mattias Spångmyr, Haninge kommun.
Permission is hereby granted, free of charge, to any person obtaining a copy
of this software and associated documentation files (the "Software"), to deal
in the Software without restriction, including without limitation the rights
to use, copy, modify, merge, publish, distribute, sublicense, and/or sell
copies of the Software, and to permit persons to whom the Software is
furnished to do so, subject to the following conditions:
The above copyright notice and this permission notice shall be included in all
copies or substantial portions of the Software.
THE SOFTWARE IS PROVIDED "AS IS", WITHOUT WARRANTY OF ANY KIND, EXPRESS OR
IMPLIED, INCLUDING BUT NOT LIMITED TO THE WARRANTIES OF MERCHANTABILITY,
FITNESS FOR A PARTICULAR PURPOSE AND NONINFRINGEMENT. IN NO EVENT SHALL THE
AUTHORS OR COPYRIGHT HOLDERS BE LIABLE FOR ANY CLAIM, DAMAGES OR OTHER
LIABILITY, WHETHER IN AN ACTION OF CONTRACT, TORT OR OTHERWISE, ARISING FROM,
OUT OF OR IN CONNECTION WITH THE SOFTWARE OR THE USE OR OTHER DEALINGS IN THE
SOFTWARE.

Parameters:
- API_KEY =   # API Consumer Key
- API_SECRET =   # API Consumer Secret
- OPTIONAL_SCOPE =   # If the application requires a scope, input the scope here
- API_AUTH_URL = https://apimanager.lantmateriet.se   # URL for LM's API Authentication
- API_TOKEN_URL = /oauth2/token   # Access Token Request URL
- API_TOKEN_REVOKE_URL = /oauth2/revoke   # Access Token Revoke Request URL
- MINIMUM_TOKEN_LIFETIME = 1800   # Minimum seconds left on token before regenerating

Note: Input features to receive the access token
Input (input)
    -> ParameterFetcher
ParameterFetcher
    ATTR_LIST = _OPTIONAL_SCOPE $(OPTIONAL_SCOPE)
    -> AttributeCreator_AuthorizationKey
RetryAfterRevokation (input)
    -> HTTPCaller_GenerateAccessToken
Note: HTTPCaller_GenerateAccessToken [HTTPCaller] / Request: / Request URL: $(API_AUTH_URL)$(API_TOKEN_URL) / HTTP Method: POST / Query String Parameters: NameValuegrant_typeclient_credentialsscope@Value(_OPTIONAL_SCOPE) Headers: NameValueAuthorizationBasic @Value(__authorizationkey) Body: / Upload Data: Specify Upload Body / Upload Body: <not set> / Content Type: Text (text/plain) / Response: / Save Response Body To: Attribute / Response Body Attribute: __response_body / Response Body Encoding: <Auto Detect from HTTP Headers> / Response Headers and Status: / List Attribute for Response Headers: <not set> / Status Code Attribute: __http_status_code / Error Attribute: __error / HTTP Client Options: / Save Cookies: No / Follow Redirects: Yes / Verify SSL Certificates: Yes / Connection Timeout Length (seconds): 60 / Transfer Timeout Length (seconds): 90
Note: Request a new Access Token
HTTPCaller_GenerateAccessToken
    ADDITIONAL_URL_PARAMETERS = grant_type;client_credentials scope;@Value(_OPTIONAL_SCOPE)
    CONNECTION_TIMEOUT_LENGTH = 60
    CUSTOM_HEADERS = Authorization;Basic @Value(__authorizationkey)
    ERROR_ATTR = __error
    FOLLOW_REDIRECTS = Yes
    HTTP_METHOD = POST
    SAVE_FILE = Attribute
    STATUS_CODE_ATTR = __http_status_code
    TARGET_ATTR = __response_body
    TARGET_ATTR_ENCODING = auto-detect
    TARGET_URL = $(API_AUTH_URL)$(API_TOKEN_URL)
    TRANSFER_TIMEOUT_LENGTH = 90
    UPLOAD_CONTENT_TYPE = Text (text/plain)
    UPLOAD_TYPE = Specify Upload Body
    USE_COOKIES = No
    VERIFY_SSL_CERTIFICATES = Yes
    -> JSONExtractor_Token
    <REJECTED> -> StringConcatenator_6
Note: Extract the response values
JSONExtractor_Token
    EXTRACT_QUERY_TABLE = _access_token json["access_token"] _scope json["scope"] _token_type json["token_type"] _expires_in json["expires_in"]
    JSON_DOCUMENT = @Value(__response_body)
    READ_FROM_FILE = NO
    EVALUATED -> Tester_TokenExpiresSoon
    <REJECTED> -> StringConcatenator_2
Note: Check if the token is expiring soon
Tester_TokenExpiresSoon
    BOOL_OP = OR
    TEST_CLAUSE = TEST @Value(_expires_in) < $(MINIMUM_TOKEN_LIFETIME)
    TEST_MODE = TEST
    PASSED -> HTTPCaller_RevokeAccessToken
    FAILED -> AttributeRemover_ClearUnnecessary
Note: Remove unwanted attributes
AttributeRemover_ClearUnnecessary
    REMOVE_ATTRS = __response_body,__http_status_code,__creation_instance,__authorizationkey
    -> OutputWithToken (output)
OutputWithToken (output)
Note: HTTPCaller_RevokeAccessToken [HTTPCaller] / Request: / Request URL: $(API_AUTH_URL)$(API_TOKEN_REVOKE_URL) / HTTP Method: POST / Query String Parameters: NameValuetoken@Value(_access_token) Headers: NameValueAuthorizationBasic @Value(__authorizationkey) Body: / Upload Data: Specify Upload Body / Upload Body: <not set> / Content Type: Text (text/plain) / Response: / Save Response Body To: Attribute / Response Body Attribute: __response_body / Response Body Encoding: <Auto Detect from HTTP Headers> / Response Headers and Status: / List Attribute for Response Headers: <not set> / Status Code Attribute: __http_status_code / Error Attribute: __error / HTTP Client Options: / Save Cookies: No / Follow Redirects: Yes / Verify SSL Certificates: Yes / Connection Timeout Length (seconds): 60 / Transfer Timeout Length (seconds): 90
Note: Revoke an old access token so that a new one can be generated.
HTTPCaller_RevokeAccessToken
    ADDITIONAL_URL_PARAMETERS = token;@Value(_access_token)
    CONNECTION_TIMEOUT_LENGTH = 60
    CUSTOM_HEADERS = Authorization;Basic @Value(__authorizationkey)
    ERROR_ATTR = __error
    FOLLOW_REDIRECTS = Yes
    HTTP_METHOD = POST
    SAVE_FILE = Attribute
    STATUS_CODE_ATTR = __http_status_code
    TARGET_ATTR = __response_body
    TARGET_ATTR_ENCODING = auto-detect
    TARGET_URL = $(API_AUTH_URL)$(API_TOKEN_REVOKE_URL)
    TRANSFER_TIMEOUT_LENGTH = 90
    UPLOAD_CONTENT_TYPE = Text (text/plain)
    UPLOAD_TYPE = Specify Upload Body
    USE_COOKIES = No
    VERIFY_SSL_CERTIFICATES = Yes
    -> RetryAfterRevokation (output)
    <REJECTED> -> StringConcatenator_3
RetryAfterRevokation (output)
<Rejected> (output)

Bookmark: Autorization Key
Note: Create and encode the authorization string from the consumer key and consumer secret
AttributeCreator_AuthorizationKey
    ATTR_TABLE = SET_TO __authorizationkey = $(API_KEY):$(API_SECRET)
    -> TextEncoder_AuthorizationKey
TextEncoder_AuthorizationKey
    DEST_ATTR = __authorizationkey
    ENCODING_TYPE = BASE64_ENCODE
    STRING_TO_ENCODE = @Value(__authorizationkey)
    -> HTTPCaller_GenerateAccessToken

Bookmark: Rejected meddelande
StringConcatenator_3
    ACTION = Create New Attribute
    PARM_LINE:
      fme_basicstring:40%1%14%1%26%1%9%1%10%1%15%1%14%1%26%1%13%1%23:Generering av access token misslyckades.
      Felmeddelande:
      @Value(fme_rejection_code)
      HTTP-fel:
      Meddelande
      @Value(__error)
      HTTP-statuskod
      @Value(__http_status_code)
      Response body
      @Value(__response_body)
    VAL_ATTR = Logg
    -> <Rejected> (output)
StringConcatenator_2
    ACTION = Create New Attribute
    PARM_LINE:
      fme_basicstring:26%1%14%1%26:JSON-parsing misslyckades.
      Felmeddelande:
      @Value(fme_rejection_code)
    VAL_ATTR = Logg
    -> <Rejected> (output)
StringConcatenator_6
    ACTION = Create New Attribute
    PARM_LINE:
      fme_basicstring:40%1%14%1%26%1%9%1%10%1%15%1%14%1%26%1%13%1%23:Generering av access token misslyckades.
      Felmeddelande:
      @Value(fme_rejection_code)
      HTTP-fel:
      Meddelande
      @Value(__error)
      HTTP-statuskod
      @Value(__http_status_code)
      Response body
      @Value(__response_body)
    VAL_ATTR = Logg
    -> <Rejected> (output)

FME custom transformer LantmaterietAPIDeliveryRequestor
LantmaterietAPIDeliveryRequestor
Requests updated data deliveries from the "Geotorget-Order - v2" API of Lantmäteriet, the Swedish mapping, cadastral and land registration authority.
Checks the current delivery status of every input Order and requests new deliveries if they are older than a specified number of hours.
Use the custom transformer LantmaterietAPIAccessTokenFetcher before this one to generate the access token parameter.
Download links for the files in the requested delivieries can be fetched using the LantmaterietAPIDownloadLinkFetcher.
Create an Application, subscribe to the "Geotorget-Order - v2" API and generate keys for your application at:
https://apimanager.lantmateriet.se/store/
Parameters
_ORDERID
An attribute holding the order id to download from.
_ACCESS_TOKEN
An attribute holding a valid access token for Lantmäteriet's API. Can be generated by the "LantmaterietAPIAccessTokenFetcher" custom transformer.
MAX_DELIVERY_AGE
How old the most recent delivery (if any) is allowed to be before requesting a new delivery. Take care to allow enough time for the delivery to be completed - otherwise a new one will be requested as soon as the last one completes and it will never download.
API_BASE_URL
The base URL for the API endpoints, e g https://api.lantmateriet.se
API_DELIVERY_URL
The API's endpoint for reading delivery info (excluding the base URL)
API_PLACE_ORDER_URL
The API's endpoint for requesting a new delivery from an existing order (excluding the base URL)
License
MIT License
Copyright © 2021, Mattias Spångmyr, Haninge kommun.
Permission is hereby granted, free of charge, to any person obtaining a copy
of this software and associated documentation files (the "Software"), to deal
in the Software without restriction, including without limitation the rights
to use, copy, modify, merge, publish, distribute, sublicense, and/or sell
copies of the Software, and to permit persons to whom the Software is
furnished to do so, subject to the following conditions:
The above copyright notice and this permission notice shall be included in all
copies or substantial portions of the Software.
THE SOFTWARE IS PROVIDED "AS IS", WITHOUT WARRANTY OF ANY KIND, EXPRESS OR
IMPLIED, INCLUDING BUT NOT LIMITED TO THE WARRANTIES OF MERCHANTABILITY,
FITNESS FOR A PARTICULAR PURPOSE AND NONINFRINGEMENT. IN NO EVENT SHALL THE
AUTHORS OR COPYRIGHT HOLDERS BE LIABLE FOR ANY CLAIM, DAMAGES OR OTHER
LIABILITY, WHETHER IN AN ACTION OF CONTRACT, TORT OR OTHERWISE, ARISING FROM,
OUT OF OR IN CONNECTION WITH THE SOFTWARE OR THE USE OR OTHER DEALINGS IN THE
SOFTWARE.

Parameters:
- OnlyOrder = 0   # Lägger endast ny beställning av leverans på befintliga ordrar (värde 1)
- _ORDERID = @Value(_orderid)   # Orderid
- _ACCESS_TOKEN = @Value(_access_token)   # Access Token
- MAX_DELIVERY_AGE = 6   # Maximum age (h) of latest delivery to order a new one
- API_BASE_URL = https://api.lantmateriet.se   # URL for Lantmäteriet's API
- API_DELIVERY_URL = /geotorget/nedladdning/v1/{OrderID}/leverans/latest   # URL for "Läs senaste leverans för order"
- API_PLACE_ORDER_URL = /geotorget/nedladdning/v1/{OrderID}/leverans   # URL for "Skapa ny leverans"

OrderIds (input)
    -> Tester
Note: Testar om endast ny beställning av leverans
Tester
    BOOL_OP = OR
    TEST_CLAUSE = TEST $(OnlyOrder) = 1
    TEST_MODE = TEST
    PASSED -> AttributeCreator
    FAILED -> Decelerator
Note: Pause / stannar upp för att invänta LM:s leveransrapport
Decelerator
    DECEL_TYPE = Per Feature Delay
    DELAY = 10
    -> ParameterFetcher
ParameterFetcher
    ATTR_LIST = _API_BASE_URL $(API_BASE_URL) _API_DELIVERY_URL $(API_DELIVERY_URL)
    -> StringReplacer
StringReplacer
    CASE = NO
    FIND_TEXT = {OrderID}
    NO_MATCH = _FME_NO_OP_
    REGEXP = NO
    REPLACE_TEXT = @Value(_orderid)
    SRC_ATTRS = _API_DELIVERY_URL
    -> StringConcatenator
StringConcatenator
    ACTION = Create New Attribute
    PARM_LINE = fme_basicstring:21%25:@Value(_API_BASE_URL)@Value(_API_DELIVERY_URL)
    VAL_ATTR = _order_url
    -> HTTPCaller_CheckDelivery
AttributeCreator
    ATTR_TABLE = SET_TO __status = MAKULERAD
    -> TestFilter_DetermineAction
Note: Determine what action to take. / Request a new delivery if the last delivery failed or it succeeded but is too old.
TestFilter_DetermineAction
    DEFAULT_VALUE = Pending Delivery
    PASSED_TEST_GROUP_OUTPUT = FIRST
    TEST_LIST:
      "BOOL_OP,COMPOSITE,COMPOSITE_TEST,""""""1 OR 2 OR ( 3 AND 4 )"""""",TEST_CLAUSE,TEST @Value(__status) = MISSLYCKAD
      TEST @Value(__status) = MAKULERAD
      TEST @Value(__status) = LYCKAD
      TEST @Value(__result_interval) > $(MAX_DELIVERY_AGE)",Request New Delivery,"BOOL_OP,OR,COMPOSITE_TEST,""""""1"""""",TEST_CLAUSE,TEST @Value(__status) = LYCKAD",Ready for Download
    Request New Delivery -> Logger_RequestingDelivery
    Ready for Download -> AttributeCreator__sortorder_1
    Pending Delivery -> AttributeCreator__sortorder_2
Logger_RequestingDelivery
    LOG_FEATURE = NONE
    MAXFEATS = 99999
    MESSAGE = Requesting new delivery from order: @Value(_orderid)
    SEVERITY = INFO
    LOGGED -> ParameterFetcher_2
ParameterFetcher_2
    ATTR_LIST = _API_BASE_URL $(API_BASE_URL) _API_PLACE_ORDER_URL $(API_PLACE_ORDER_URL)
    -> StringReplacer_2
StringReplacer_2
    CASE = NO
    FIND_TEXT = {OrderID}
    NO_MATCH = _FME_NO_OP_
    REGEXP = NO
    REPLACE_TEXT = @Value(_orderid)
    SRC_ATTRS = _API_PLACE_ORDER_URL
    -> StringConcatenator_5
StringConcatenator_5
    ACTION = Create New Attribute
    PARM_LINE = fme_basicstring:21%28:@Value(_API_BASE_URL)@Value(_API_PLACE_ORDER_URL)
    VAL_ATTR = _order_url
    -> HTTPCaller_PlaceOrder
Note: Request a new delivery for an existing order (subscription)
Note: HTTPCaller_PlaceOrder [HTTPCaller] / Request: / Request URL: @Value(_order_url) / HTTP Method: POST / Query String Parameters: / Query String: <not set> / Headers: NameValueAuthorizationBearer @Value(_access_token) Body: / Upload Data: Specify Upload Body / Upload Body: { "payload": "string" } / Content Type: JSON (application/json) / Response: / Save Response Body To: Attribute / Response Body Attribute: __response_body / Response Body Encoding: <Auto Detect from HTTP Headers> / Response Headers and Status: / List Attribute for Response Headers: <not set> / Status Code Attribute: __http_status_code / Error Attribute: __error / HTTP Client Options: / Save Cookies: No / Follow Redirects: Yes / Verify SSL Certificates: Yes / Connection Timeout Length (seconds): 60 / Transfer Timeout Length (seconds): 90
HTTPCaller_PlaceOrder
    CONNECTION_TIMEOUT_LENGTH = 60
    CUSTOM_HEADERS = Authorization;Bearer @Value(_access_token)
    ERROR_ATTR = __error
    FOLLOW_REDIRECTS = Yes
    HTTP_METHOD = POST
    SAVE_FILE = Attribute
    STATUS_CODE_ATTR = __http_status_code
    TARGET_ATTR = __response_body
    TARGET_ATTR_ENCODING = auto-detect
    TARGET_URL = @Value(_order_url)
    TRANSFER_TIMEOUT_LENGTH = 90
    UPLOAD_BODY = { "payload": "string" }
    UPLOAD_CONTENT_TYPE = JSON (application/json)
    UPLOAD_TYPE = Specify Upload Body
    USE_COOKIES = No
    VERIFY_SSL_CERTIFICATES = Yes
    -> AttributeCreator__sortorder_3
AttributeCreator__sortorder_3
    ATTR_TABLE = SET_TO __sortorder = 3
    -> Sorter
AttributeCreator__sortorder_1
    ATTR_TABLE = SET_TO __sortorder = 1
    -> Logger_ReadyForDownload
Logger_ReadyForDownload
    LOG_FEATURE = NONE
    MAXFEATS = 99999
    MESSAGE = Found a recent delivery from order: @Value(_orderid)
    SEVERITY = INFO
    LOGGED -> Sorter
AttributeCreator__sortorder_2
    ATTR_TABLE = SET_TO __sortorder = 2
    -> Logger_PendingDelivery
Logger_PendingDelivery
    LOG_FEATURE = NONE
    MAXFEATS = 99999
    MESSAGE = Found a pending delivery from order: @Value(_orderid)
    SEVERITY = INFO
    LOGGED -> Sorter
Note: Make sure all requests are made before releasing any features (which would stall further requests). / Also put already finished deliveries first in line, followed by pending deliveries and lastly, deliveries that were just requested.
Sorter
    SORT_PARM = __sortorder NUMERIC ASCENDING
    SORTED -> AttributeRemover_ClearUnnecessary
Note: Remove unwanted attributes
AttributeRemover_ClearUnnecessary
    REMOVE_ATTRS = __response_body,__http_status_code,__result_interval,__sortorder,__timestamp
    -> ReadyOrPending (output)
ReadyOrPending (output)

Bookmark: Read dealivery info
Note: HTTPCaller_CheckDelivery [HTTPCaller] / Request: / Request URL: @Value(_order_url) / HTTP Method: GET / Query String Parameters: / Query String: <not set> / Headers: NameValueAuthorizationBearer @Value(_access_token)Response: / Save Response Body To: Attribute / Response Body Attribute: __response_body / Response Body Encoding: <Auto Detect from HTTP Headers> / Response Headers and Status: / List Attribute for Response Headers: <not set> / Status Code Attribute: __http_status_code / Error Attribute: __error / HTTP Client Options: / Save Cookies: No / Follow Redirects: Yes / Verify SSL Certificates: Yes / Connection Timeout Length (seconds): 60 / Transfer Timeout Length (seconds): 90
HTTPCaller_CheckDelivery
    CONNECTION_TIMEOUT_LENGTH = 60
    CUSTOM_HEADERS = Authorization;Bearer @Value(_access_token)
    ERROR_ATTR = __error
    FOLLOW_REDIRECTS = Yes
    HTTP_METHOD = GET
    SAVE_FILE = Attribute
    STATUS_CODE_ATTR = __http_status_code
    TARGET_ATTR = __response_body
    TARGET_ATTR_ENCODING = auto-detect
    TARGET_URL = @Value(_order_url)
    TRANSFER_TIMEOUT_LENGTH = 90
    USE_COOKIES = No
    VERIFY_SSL_CERTIFICATES = Yes
    -> JSONExtractor_Delivery
    <REJECTED> -> StringConcatenator_6
JSONExtractor_Delivery
    EXTRACT_QUERY_TABLE = __uppdaterad JSON["uppdaterad"] __status JSON["status"]
    JSON_DOCUMENT = @Value(__response_body)
    READ_FROM_FILE = NO
    EVALUATED -> DateTimeStamper_Now
    <REJECTED> -> StringConcatenator_2

Bookmark: Calculate the age of the latest delivery
DateTimeStamper_Now
    DATETIME_ATTR = __timestamp
    INCLUDE_OFFSET = YES
    STAMP_TYPE = datetime
    TIMEZONE = utc
    -> DateTimeConverter
DateTimeConverter
    DATETIME_ATTR = __uppdaterad
    OUT_FORMAT = FME
    PASSTHROUGH = YES
    REPAIR_INPUT = YES
    -> Tester_MissingUpdateTime
    <REJECTED> -> StringConcatenator_3
Tester_MissingUpdateTime
    BOOL_OP = OR
    TEST_CLAUSE = TEST __uppdaterad NOT_ATTRIBUTE_HAS_A_VALUE ""
    TEST_MODE = TEST
    PASSED -> TestFilter_DetermineAction
    FAILED -> DateTimeCalculator_Hours
DateTimeCalculator_Hours
    MODE = DATETIMECALC_3_CALCULATE_INTERVAL
    OPERATION_PARAMETERS = START_DATETIME]@Value(__uppdaterad)]END_DATETIME]@Value(__timestamp)]RESULT_TYPE]HOURS]RESULT_INTERVAL]__result_interval]FME_CONTROLLER_QUERY_FILE]transformers/dependencies/datetimecalculator/DATETIMECALC_3_CALCULATE_INTERVAL.fme
    -> TestFilter_DetermineAction
    <REJECTED> -> StringConcatenator_4

Bookmark: Rejected meddelande
StringConcatenator_4
    ACTION = Create New Attribute
    PARM_LINE:
      fme_basicstring:85%1%14%1%26:Beräkning av timmar mellan maximal leveransålder och hämtningstillfälle misslyckades.
      Felmeddelande:
      @Value(fme_rejection_code)
    VAL_ATTR = Logg
    -> Junction
StringConcatenator_3
    ACTION = Create New Attribute
    PARM_LINE:
      fme_basicstring:40%1%14%1%26:Datum- och tidkonvertering misslyckades.
      Felmeddelande:
      @Value(fme_rejection_code)
    VAL_ATTR = Logg
    -> Junction
StringConcatenator_2
    ACTION = Create New Attribute
    PARM_LINE:
      fme_basicstring:26%1%14%1%26:JSON-parsing misslyckades.
      Felmeddelande:
      @Value(fme_rejection_code)
    VAL_ATTR = Logg
    -> Junction
StringConcatenator_6
    ACTION = Create New Attribute
    PARM_LINE:
      fme_basicstring:40%1%14%1%26%1%9%1%10%1%15%1%14%1%26%1%13%1%23:Kontroll av leveransstatus misslyckades.
      Felmeddelande:
      @Value(fme_rejection_code)
      HTTP-fel:
      Meddelande
      @Value(__error)
      HTTP-statuskod
      @Value(__http_status_code)
      Response body
      @Value(__response_body)
    VAL_ATTR = Logg
    -> Junction
Junction
    -> <Rejected> (output)
<Rejected> (output)

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    INCLUDE_OFFSET = NO
    STAMP_TYPE = datetime
    TIMEZONE = local
    -> DateTimeConverter
DateTimeConverter
    DATETIME_ATTR = _dts
    OUT_FORMAT = %Y-%m-%d %H:%M:%S
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    NO_MATCH = _FME_NO_OP_
    REGEXP = YES
    SRC_ATTRS = _dts
    -> StringReplacer_2
StringReplacer_2
    CASE = NO
    FIND_TEXT = .*\.
    NO_MATCH = _FME_NO_OP_
    REGEXP = YES
    SRC_ATTRS = _mils
    -> SubstringExtractor
SubstringExtractor
    END = 2
    RESULT_ATTR = _subMils
    SRC_STRING = @Value(_mils)
    START = 0
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)

FME custom transformer LantmaterietAPIDownloadLinkFetcher
LantmaterietAPIDownloadLinkFetcher
Fetches download links from the "Geotorget-Order - v2" API of Lantmäteriet, the Swedish mapping, cadastral and land registration authority.
Checks the delivery status of each input Order and, if its ready, returns a set of download links (one feature per link).
Checks back in with a specified interval until a delivery is ready to download (its status has become "LYCKAD").
Use the custom transformer LantmaterietAPIAccessTokenFetcher to generate the access token parameter.
Use the LantmaterietAPIDeliveryRequestor before this one to request updated deliveries for your Orders.
Create an Application, subscribe to the "Geotorget-Order - v2" API and generate keys for your application at:
https://apimanager.lantmateriet.se/store/
Parameters
_ORDERID
An attribute holding the order id to download from.
_ACCESS_TOKEN
An attribute holding a valid access token for Lantmäteriet's API. Can be generated by the "LantmaterietAPIAccessTokenFetcher" custom transformer.
API_BASE_URL
The base URL for the API endpoints, e g https://api.lantmateriet.se
API_DELIVERY_URL
The API's endpoint for reading delivery info (excluding the base URL)
API_DOWNLOAD_URL
The API's URL for getting a list of download links for an existing order.
STATUS_REQUEST_INTERVAL
Number of seconds between status requests (while waiting for pending deliveries).
License
MIT License
Copyright © 2021, Mattias Spångmyr, Haninge kommun.
Permission is hereby granted, free of charge, to any person obtaining a copy
of this software and associated documentation files (the "Software"), to deal
in the Software without restriction, including without limitation the rights
to use, copy, modify, merge, publish, distribute, sublicense, and/or sell
copies of the Software, and to permit persons to whom the Software is
furnished to do so, subject to the following conditions:
The above copyright notice and this permission notice shall be included in all
copies or substantial portions of the Software.
THE SOFTWARE IS PROVIDED "AS IS", WITHOUT WARRANTY OF ANY KIND, EXPRESS OR
IMPLIED, INCLUDING BUT NOT LIMITED TO THE WARRANTIES OF MERCHANTABILITY,
FITNESS FOR A PARTICULAR PURPOSE AND NONINFRINGEMENT. IN NO EVENT SHALL THE
AUTHORS OR COPYRIGHT HOLDERS BE LIABLE FOR ANY CLAIM, DAMAGES OR OTHER
LIABILITY, WHETHER IN AN ACTION OF CONTRACT, TORT OR OTHERWISE, ARISING FROM,
OUT OF OR IN CONNECTION WITH THE SOFTWARE OR THE USE OR OTHER DEALINGS IN THE
SOFTWARE.

Parameters:
- _ORDERID = @Value(_orderid)   # Orderid
- _ACCESS_TOKEN = @Value(_access_token)   # Access Token
- API_BASE_URL = https://api.lantmateriet.se   # URL for Lantmäteriet's API
- API_DELIVERY_URL = /geotorget/nedladdning/v1/{OrderID}/leverans/latest   # URL for "Läs senaste leverans för order"
- API_DOWNLOAD_URL = /geotorget/nedladdning/v1/{OrderID}/leverans/latest/files   # URL for "Ladda hem leverans"
- STATUS_REQUEST_INTERVAL = 30   # Seconds between status requests after placing new orders

Retries (input)
    -> Logger_Retry
Logger_Retry
    LOG_FEATURE = NONE
    MAXFEATS = 99999
    MESSAGE = Retrying with order: (@Value(__orderid))
    SEVERITY = INFO
    LOGGED -> Decelerator_WaitXSeconds
Note: Limit the status request interval
Decelerator_WaitXSeconds
    DECEL_TYPE = Limit Features Per Second
    FEATURES_PER_SECOND = 1/$(STATUS_REQUEST_INTERVAL)
    -> HTTPCaller_CheckDelivery
    <REJECTED> -> StringConcatenator_3
Note: Original orders
OrderIds (input)
    -> AttributeCopier_Input
AttributeCopier_Input
    ATTR_TABLE:
      COPY _orderid > __orderid
      COPY _access_token > __access_token
    -> Logger_InputOrder
Logger_InputOrder
    LOG_FEATURE = NONE
    MAXFEATS = 99999
    MESSAGE = Handling downloads from order: (@Value(__orderid))
    SEVERITY = INFO
    LOGGED -> ParameterFetcher
ParameterFetcher
    ATTR_LIST = _API_BASE_URL $(API_BASE_URL) _API_DELIVERY_URL $(API_DELIVERY_URL)
    -> StringReplacer
StringReplacer
    CASE = NO
    FIND_TEXT = {OrderID}
    NO_MATCH = _FME_NO_OP_
    REGEXP = NO
    REPLACE_TEXT = @Value(__orderid)
    SRC_ATTRS = _API_DELIVERY_URL
    -> StringConcatenator
StringConcatenator
    ACTION = Create New Attribute
    PARM_LINE = fme_basicstring:21%25:@Value(_API_BASE_URL)@Value(_API_DELIVERY_URL)
    VAL_ATTR = _order_url
    -> HTTPCaller_CheckDelivery
Note: If the delivery status is "LYCKAD"; proceed to fetch download links. / Otherwise, retry later.
TestFilter_DetermineAction
    DEFAULT_VALUE = Try again later
    PASSED_TEST_GROUP_OUTPUT = FIRST
    TEST_LIST = "BOOL_OP,OR,COMPOSITE_TEST,""""""1"""""",TEST_CLAUSE,TEST @Value(__status) = LYCKAD",Download
    Download -> Logger_Downloading
    Try again later -> Retries (output)
Logger_Downloading
    LOG_FEATURE = NONE
    MAXFEATS = 99999
    MESSAGE = Downloading from order: @Value(__orderid)
    SEVERITY = INFO
    LOGGED -> ParameterFetcher_2
ParameterFetcher_2
    ATTR_LIST = _API_BASE_URL $(API_BASE_URL) _API_DOWNLOAD_URL $(API_DOWNLOAD_URL)
    -> StringReplacer_2
StringReplacer_2
    CASE = NO
    FIND_TEXT = {OrderID}
    NO_MATCH = _FME_NO_OP_
    REGEXP = NO
    REPLACE_TEXT = @Value(_orderid)
    SRC_ATTRS = _API_DOWNLOAD_URL
    -> StringConcatenator_9
StringConcatenator_9
    ACTION = Create New Attribute
    PARM_LINE = fme_basicstring:21%25:@Value(_API_BASE_URL)@Value(_API_DOWNLOAD_URL)
    VAL_ATTR = _download_url
    -> HTTPCaller_DownloadList
DownloadLinks (output)
Retries (output)
<Rejected> (output)

Bookmark: Rejected meddelande
StringConcatenator_3
    ACTION = Create New Attribute
    PARM_LINE:
      fme_basicstring:56%1%14%1%26:Begränsning av leveransstatusförfrågningar misslyckades.
      Felmeddelande:
      @Value(fme_rejection_code)
    VAL_ATTR = Logg
    -> Junction_2
StringConcatenator_8
    ACTION = Create New Attribute
    PARM_LINE:
      fme_basicstring:26%1%14%1%26:JSON-parsing misslyckades.
      Felmeddelande:
      @Value(fme_rejection_code)
    VAL_ATTR = Logg
    -> <Rejected> (output)
StringConcatenator_7
    ACTION = Create New Attribute
    PARM_LINE:
      fme_basicstring:45%1%14%1%26%1%9%1%10%1%15%1%14%1%26%1%13%1%23:Förfrågan om nedladdningslänkar misslyckades.
      Felmeddelande:
      @Value(fme_rejection_code)
      HTTP-fel:
      Meddelande
      @Value(__error)
      HTTP-statuskod
      @Value(__http_status_code)
      Response body
      @Value(__response_body)
    VAL_ATTR = Logg
    -> <Rejected> (output)
StringConcatenator_5
    ACTION = Create New Attribute
    PARM_LINE:
      fme_basicstring:85%1%14%1%26:Beräkning av timmar mellan maximal leveransålder och hämtningstillfälle misslyckades.
      Felmeddelande:
      @Value(fme_rejection_code)
    VAL_ATTR = Logg
    -> Junction
StringConcatenator_4
    ACTION = Create New Attribute
    PARM_LINE:
      fme_basicstring:40%1%14%1%26:Datum- och tidkonvertering misslyckades.
      Felmeddelande:
      @Value(fme_rejection_code)
    VAL_ATTR = Logg
    -> Junction
StringConcatenator_2
    ACTION = Create New Attribute
    PARM_LINE:
      fme_basicstring:26%1%14%1%26:JSON-parsing misslyckades.
      Felmeddelande:
      @Value(fme_rejection_code)
    VAL_ATTR = Logg
    -> Junction_2
StringConcatenator_6
    ACTION = Create New Attribute
    PARM_LINE:
      fme_basicstring:40%1%14%1%26%1%9%1%10%1%15%1%14%1%26%1%13%1%23:Kontroll av leveransstatus misslyckades.
      Felmeddelande:
      @Value(fme_rejection_code)
      HTTP-fel:
      Meddelande
      @Value(__error)
      HTTP-statuskod
      @Value(__http_status_code)
      Response body
      @Value(__response_body)
    VAL_ATTR = Logg
    -> Junction_2
Junction_2
    -> Junction
Junction
    -> <Rejected> (output)

Bookmark: Read dealivery info
Note: HTTPCaller_CheckDelivery [HTTPCaller] / Request: / Request URL: @Value(_order_url) / HTTP Method: GET / Query String Parameters: / Query String: <not set> / Headers: NameValueAuthorizationBearer @Value(__access_token)Response: / Save Response Body To: Attribute / Response Body Attribute: __response_body / Response Body Encoding: <Auto Detect from HTTP Headers> / Response Headers and Status: / List Attribute for Response Headers: <not set> / Status Code Attribute: __http_status_code / Error Attribute: __error / HTTP Client Options: / Save Cookies: No / Follow Redirects: Yes / Verify SSL Certificates: Yes / Connection Timeout Length (seconds): 60 / Transfer Timeout Length (seconds): 90
HTTPCaller_CheckDelivery
    CONNECTION_TIMEOUT_LENGTH = 60
    CUSTOM_HEADERS = Authorization;Bearer @Value(__access_token)
    ERROR_ATTR = __error
    FOLLOW_REDIRECTS = Yes
    HTTP_METHOD = GET
    SAVE_FILE = Attribute
    STATUS_CODE_ATTR = __http_status_code
    TARGET_ATTR = __response_body
    TARGET_ATTR_ENCODING = auto-detect
    TARGET_URL = @Value(_order_url)
    TRANSFER_TIMEOUT_LENGTH = 90
    USE_COOKIES = No
    VERIFY_SSL_CERTIFICATES = Yes
    -> JSONExtractor_Delivery
    <REJECTED> -> StringConcatenator_6
JSONExtractor_Delivery
    EXTRACT_QUERY_TABLE = __uppdaterad JSON["uppdaterad"] __status JSON["status"]
    JSON_DOCUMENT = @Value(__response_body)
    READ_FROM_FILE = NO
    EVALUATED -> DateTimeStamper_Now
    <REJECTED> -> StringConcatenator_2

Bookmark: Calculate the age of the latest delivery
DateTimeStamper_Now
    DATETIME_ATTR = __timestamp
    INCLUDE_OFFSET = YES
    STAMP_TYPE = datetime
    TIMEZONE = utc
    -> DateTimeConverter
DateTimeConverter
    DATETIME_ATTR = __uppdaterad
    OUT_FORMAT = FME
    PASSTHROUGH = YES
    REPAIR_INPUT = YES
    -> Tester_MissingUpdateTime
    <REJECTED> -> StringConcatenator_4
Tester_MissingUpdateTime
    BOOL_OP = OR
    TEST_CLAUSE = TEST __uppdaterad NOT_ATTRIBUTE_HAS_A_VALUE ""
    TEST_MODE = TEST
    PASSED -> TestFilter_DetermineAction
    FAILED -> DateTimeCalculator_Hours
DateTimeCalculator_Hours
    MODE = DATETIMECALC_3_CALCULATE_INTERVAL
    OPERATION_PARAMETERS = START_DATETIME]@Value(__uppdaterad)]END_DATETIME]@Value(__timestamp)]RESULT_TYPE]HOURS]RESULT_INTERVAL]__result_interval]FME_CONTROLLER_QUERY_FILE]transformers/dependencies/datetimecalculator/DATETIMECALC_3_CALCULATE_INTERVAL.fme
    -> TestFilter_DetermineAction
    <REJECTED> -> StringConcatenator_5

Bookmark: Fetch download links for each order
Note: HTTPCaller_DownloadList [HTTPCaller] / Request: / Request URL: @Value(_download_url) / HTTP Method: GET / Query String Parameters: / Query String: <not set> / Headers: NameValueAuthorizationBearer @Value(__access_token)Response: / Save Response Body To: Attribute / Response Body Attribute: __response_body / Response Body Encoding: <Auto Detect from HTTP Headers> / Response Headers and Status: / List Attribute for Response Headers: <not set> / Status Code Attribute: __http_status_code / Error Attribute: __error / HTTP Client Options: / Save Cookies: No / Follow Redirects: Yes / Verify SSL Certificates: Yes / Connection Timeout Length (seconds): 60 / Transfer Timeout Length (seconds): 90
HTTPCaller_DownloadList
    CONNECTION_TIMEOUT_LENGTH = 60
    CUSTOM_HEADERS = Authorization;Bearer @Value(__access_token)
    ERROR_ATTR = __error
    FOLLOW_REDIRECTS = Yes
    HTTP_METHOD = GET
    SAVE_FILE = Attribute
    STATUS_CODE_ATTR = __http_status_code
    TARGET_ATTR = __response_body
    TARGET_ATTR_ENCODING = auto-detect
    TARGET_URL = @Value(_download_url)
    TRANSFER_TIMEOUT_LENGTH = 90
    USE_COOKIES = No
    VERIFY_SSL_CERTIFICATES = Yes
    -> JSONFragmenter_DownloadLinks
    <REJECTED> -> StringConcatenator_7
JSONFragmenter_DownloadLinks
    EXPLODE_FORMAT = JSON
    EXTRACT_ATTR = Yes
    JSON_ATTR = __response_body
    JSON_QUERY = json[*]
    NEW_ATTRIBUTES = path title
    READ_FROM_FILE = NO
    RECURSIVE = No
    REJECT_EMPTY_LISTS = YES
    FRAGMENTS -> AttributeRenamer
    <REJECTED> -> StringConcatenator_8

Bookmark: Specify output attributes
AttributeRenamer
    ATTR_TABLE:
      RENAME_SET_DEFAULT path > __href
      RENAME_SET_DEFAULT title > __title
    -> AttributeRemover
AttributeRemover
    REMOVE_ATTRS = __http_status_code,__response_body,__result_interval,__status,__timestamp,_access_token,_orderid,json_index,json_type
    -> DownloadLinks (output)
