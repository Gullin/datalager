FME workspace oracle-topo_ndrk-DatalagerManage-driver.fmw

Parameters:
- RotDirectory = ../   # Katalogen där processen startar
- ProcessName =   # Processnamn
- OutputDirectory = C:\LKR_GIS\Datalager_procsrc\_geodatarepo\landskrona\lkr_gis   # Katalog för lagring av del av datalager
- ProcessModulName =   # Processmodulsnamn
- IsWholeProcessRun = 1   # Är hela datalagerprocessen körd
- SchemaFlush = $(RotDirectory)$(ProcessModulName)/_schema/schema-flush.xlsx   # Schemaspecifikation för aktuellt data

Readers:
- XLSXR_1: XLSXR from $(SchemaFlush)

Creator
    GEOMTYPE = Geometry Object
    NUM = 1
    CREATED -> ParameterFetcher_2
ParameterFetcher_2
    ATTR_LIST = ProcessName $(ProcessName) RotDirectory $(RotDirectory)
    -> StringConcatenator_8
StringConcatenator_8
    VAL_ATTR = ProcessName_DRIVER
    ACTION = Create New Attribute
    PARM_LINE = @Value(ProcessName)_DRIVER
    -> UUIDGenerator_2
UUIDGenerator_2
    UUID_ATTR = ProcessID
    -> AttributeCreator_12
AttributeCreator_12
    ATTR_TABLE = SET_TO _FeatureIdMerger = 1
    -> AttributeCreator_12_OUTPUT_-__FeatureMerger_3_SUPPLIER
AttributeCreator_12_OUTPUT_-__FeatureMerger_3_SUPPLIER: Junction
    -> Junction
    -> Junction_3
    -> Junction_5
    -> Junction_7
    -> Junction_9
Note: FeatureMerger_2 : Supplier
Junction
    -> Junction_2
Note: FeatureMerger_3 : Supplier
Junction_3
    -> Junction_4
Note: FeatureMerger_4 : Supplier
Junction_5
    -> Junction_6
Note: FeatureMerger_5 : Supplier
Junction_7
    -> Junction_8
Note: FeatureMerger_6 : Supplier
Junction_9
    -> Junction_10
Note: Parametrar / * [RotDirectory] Kommer från batch-processen och är obligatoriskt för alla FME-processor. / * [ProcessName] Kommer från batch-processen och är obligatoriskt för alla FME-processor. / * [Manifest] Excel-fil från ett tidigare exporterat schema anpassad med nya kolumnnamn samt vilken data som ska exporteras. / * [OutputDirectory] Katalogsökväg för exporterad geodata (delrepository).
schema (reader XLSXR_1)
    attributes: fme_feature_type_name char(20), column_name char(16), dl_need_new_column_name char(6), dl_new_column_name char(12), dl_export char(5), fme_data_type char(18), native_data_type char(14), fme_format_long_name char(22), fme_format_short_name char(15), _dirpath char(1), _extension char(1), DatasetFull char(8), Dataset char(8), column_name_char_length number(3,0)
    -> Tester_4
Tester_4
    TEST_CLAUSE = TEST @Value(dl_export) = true
    BOOL_OP = OR
    TEST_DESCRIPTION = ""
    TEST_MODE = Automatic
    PASSED -> Tester_2
    PASSED -> Aggregator_3
    PASSED -> Sampler_2
Aggregator_3
    SEP = ,
    MODE = Geometry - Assemble One Level
    GROUP_BY = fme_feature_type_name fme_format_short_name Dataset
    AGGREGATE_TYPE = Homogeneous Collection (If Possible)
    ACCUM_ATTRS_NAME = Drop Incoming Attributes
    ORDERED = No
    AGGREGATE -> TestFilter
Note: Format som stöds
TestFilter
    DEFAULT_VALUE = <UNFILTERED>
    TEST_LIST = BOOL_OP,OR,COMPOSITE_TEST,<Unused>,TEST_CLAUSE,"TEST @Value(fme_format_short_name) = ORACLE_SPATIAL",ORACLE_SPATIAL
    ORACLE_SPATIAL -> WorkspaceRunner
    <UNFILTERED> -> Aggregator
WorkspaceRunner
    WORKSPACE_FILE = $(FME_MF_DIR)oracle-topo_ndrk-DatalagerManage-main-ORACLE_SPATIAL.fmw
    BLOCKING = Yes
    WORKSPACE_PARAMETERS = RotDirectory,$(RotDirectory),ProcessName,$(ProcessName),SchemaFlush,$(SchemaFlush),DatabaseSchema,@Value(Dataset),Datatable,@Value(fme_feature_type_name),OutputDirectory,$(OutputDirectory),ProcessModulName,$(ProcessModulName),IsWholeProcessRun,$(IsWholeProcessRun)
    SUCCEEDED -> AttributeCreator_2
    FAILED -> StringConcatenator_3
    SUMMARY -> AttributeCreator_3

Bookmark: Loggning
Note: AttributeCreator_12_-_FeatureMerger_3
Junction_2
    -> FeatureMerger_2 [SUPPLIER]
Note: AttributeCreator_12_-_FeatureMerger_3
Junction_4
    -> FeatureMerger_3 [SUPPLIER]
Note: AttributeCreator_12_-_FeatureMerger_3
Junction_6
    -> FeatureMerger_4 [SUPPLIER]
Note: AttributeCreator_12_-_FeatureMerger_3
Junction_8
    -> FeatureMerger_5 [SUPPLIER]
Note: AttributeCreator_12_-_FeatureMerger_3
Junction_10
    -> FeatureMerger_6 [SUPPLIER]
StringConcatenator_3
    VAL_ATTR = _result
    ACTION = Create New Attribute
    PARM_LINE = @Value(Dataset).@Value(fme_feature_type_name) (@Value(fme_format_short_name))
    -> AttributeCreator_6
AttributeCreator_6
    ATTR_TABLE = SET_TO _FeatureIdMerger = 1
    -> FeatureMerger_5 [REQUESTOR]
FeatureMerger_5
    SUPPLIERS_FIRST = No
    IGNORE_NULLS = No
    ATTR_CONFLICT_RES = Use Requestor
    ATTR_ACCUM_MODE = Merge Supplier
    JOIN_KEYS = @Value(_FeatureIdMerger) @Value(_FeatureIdMerger) AUTO
    REJECT_NULL_MISSING_KEYS = No
    PROCESS_DUPS = No
    MERGE_TYPE = Attributes Only
    MERGED -> StringConcatenator_7
StringConcatenator_7
    VAL_ATTR = Logg
    ACTION = Create New Attribute
    PARM_LINE = @Value(_result) - kunde inte exporteras. Fel: @Value(_failure_message)
    -> DTStamperYYYY-MM-DD_HH:MI:SS.sss_4
DTStamperYYYY-MM-DD_HH:MI:SS.sss_4
    -> Logg_6
Logg_6: WorkspaceRunner
    WORKSPACE_FILE = C:\dev\Datalager_procsrc\_sys\_logg.fmw
    BLOCKING = Yes
    WORKSPACE_PARAMETERS = EX_DATE_TIME,@Value(_datetimestamp),EX_PROCESS_NAME,@Value(ProcessName_DRIVER),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Sampler_5
    SAMPLE_MODE = No
    SAMPLE_TYPE_LONG = First N Features
    RATE = 1
    SAMPLED -> AttributeCreator_7
StringConcatenator_5
    VAL_ATTR = Logg
    ACTION = Create New Attribute
    PARM_LINE = Kör @Value(ProcessName_DRIVER) för data definierad i "" till datalagret.
    -> DTStamperYYYY-MM-DD_HH:MI:SS.sss_5
DTStamperYYYY-MM-DD_HH:MI:SS.sss_5
    -> Logg_5
Logg_5: WorkspaceRunner
    WORKSPACE_FILE = C:\dev\Datalager_procsrc\_sys\_logg.fmw
    BLOCKING = No
    WORKSPACE_PARAMETERS = EX_DATE_TIME,@Value(_datetimestamp),EX_PROCESS_NAME,@Value(ProcessName_DRIVER),EX_ID,@Value(ProcessID),EX_TYPE,KLART,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: Format som det ej finns stöd för men som är / definierade som exporterbara i manifest
Aggregator
    SEP = ", "
    MODE = Geometry - Assemble One Level
    GROUP_BY = fme_format_short_name
    COUNT_ATTR = Antal
    AGGREGATE_TYPE = Homogeneous Collection (If Possible)
    ACCUM_ATTRS_NAME = Use Attributes From One Feature
    ORDERED = No
    AGGREGATE -> AttributeCreator_5
AttributeCreator_5
    ATTR_TABLE = SET_TO _FeatureIdMerger = 1
    -> FeatureMerger_4 [REQUESTOR]
FeatureMerger_4
    SUPPLIERS_FIRST = No
    IGNORE_NULLS = No
    ATTR_CONFLICT_RES = Use Requestor
    ATTR_ACCUM_MODE = Merge Supplier
    JOIN_KEYS = @Value(_FeatureIdMerger) @Value(_FeatureIdMerger) AUTO
    REJECT_NULL_MISSING_KEYS = No
    PROCESS_DUPS = No
    MERGE_TYPE = Attributes Only
    MERGED -> StringConcatenator_4
StringConcatenator_4
    VAL_ATTR = Logg
    ACTION = Create New Attribute
    PARM_LINE = Följande @Value(Antal)  st. format stöds ej (@Value(fme_format_short_name)). För att export ska vara fullt möjligt enligt manifest, ändra i manifest eller definiera ny WorkspaceRunner med workspace.
    -> DTStamperYYYY-MM-DD_HH:MI:SS.sss_3
DTStamperYYYY-MM-DD_HH:MI:SS.sss_3
    -> Logg_4
Logg_4: WorkspaceRunner
    WORKSPACE_FILE = C:\dev\Datalager_procsrc\_sys\_logg.fmw
    BLOCKING = Yes
    WORKSPACE_PARAMETERS = EX_DATE_TIME,@Value(_datetimestamp),EX_PROCESS_NAME,@Value(ProcessName_DRIVER),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: Följande kolumn förekommer fler än / en gång för specifikt dataset
Aggregator_4
    SEP = ", "
    MODE = Geometry - Assemble One Level
    GROUP_BY = dl_new_column_name
    COUNT_ATTR = Antal
    AGGREGATE_TYPE = Homogeneous Collection (If Possible)
    ACCUM_ATTRS_NAME = Use Attributes From One Feature
    ORDERED = No
    AGGREGATE -> AttributeCreator_4
AttributeCreator_4
    ATTR_TABLE = SET_TO _FeatureIdMerger = 1
    -> FeatureMerger_3 [REQUESTOR]
FeatureMerger_3
    SUPPLIERS_FIRST = No
    IGNORE_NULLS = No
    ATTR_CONFLICT_RES = Use Requestor
    ATTR_ACCUM_MODE = Merge Supplier
    JOIN_KEYS = @Value(_FeatureIdMerger) @Value(_FeatureIdMerger) AUTO
    REJECT_NULL_MISSING_KEYS = No
    PROCESS_DUPS = No
    MERGE_TYPE = Attributes Only
    MERGED -> StringConcatenator_6
StringConcatenator_6
    VAL_ATTR = Logg
    ACTION = Create New Attribute
    PARM_LINE = Följande @Value(Antal)  st. kolumner finns det dubbletter för (@Value(dl_new_column_name)). För att exporterad data vara läsbar enligt manifest, ändra kolumnnamn i manifest.
    -> DTStamperYYYY-MM-DD_HH:MI:SS.sss_2
DTStamperYYYY-MM-DD_HH:MI:SS.sss_2
    -> Logg_3
Logg_3: WorkspaceRunner
    WORKSPACE_FILE = C:\dev\Datalager_procsrc\_sys\_logg.fmw
    BLOCKING = Yes
    WORKSPACE_PARAMETERS = EX_DATE_TIME,@Value(_datetimestamp),EX_PROCESS_NAME,@Value(ProcessName_DRIVER),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: Endast till för som signal att starta logg
Sampler_2
    SAMPLE_MODE = No
    SAMPLE_TYPE_LONG = First N Features
    RATE = 1
    SAMPLED -> AttributeCreator_13
AttributeCreator_13
    ATTR_TABLE = SET_TO _FeatureIdMerger = 1
    -> FeatureMerger_2 [REQUESTOR]
FeatureMerger_2
    SUPPLIERS_FIRST = No
    IGNORE_NULLS = No
    ATTR_CONFLICT_RES = Use Requestor
    ATTR_ACCUM_MODE = Merge Supplier
    JOIN_KEYS = @Value(_FeatureIdMerger) @Value(_FeatureIdMerger) AUTO
    REJECT_NULL_MISSING_KEYS = No
    PROCESS_DUPS = No
    MERGE_TYPE = Attributes Only
    MERGED -> StringConcatenator_2
StringConcatenator_2
    VAL_ATTR = Logg
    ACTION = Create New Attribute
    PARM_LINE = Kör @Value(ProcessName_DRIVER) för data definierad i "" till datalagret.
    -> DTStamperYYYY-MM-DD_HH:MI:SS.sss
DTStamperYYYY-MM-DD_HH:MI:SS.sss
    -> Logg_2
Logg_2: WorkspaceRunner
    WORKSPACE_FILE = C:\dev\Datalager_procsrc\_sys\_logg.fmw
    BLOCKING = No
    WORKSPACE_PARAMETERS = EX_DATE_TIME,@Value(_datetimestamp),EX_PROCESS_NAME,@Value(ProcessName_DRIVER),EX_ID,@Value(ProcessID),EX_TYPE,INFORMATION,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)

Bookmark: Sammanställning Succeeded och Summary
AttributeCreator_2
    ATTR_TABLE = SET_TO FeatureWR-ID = 1
    -> Aggregator_5
Aggregator_5
    SEP = ,
    MODE = Geometry - Assemble One Level
    COUNT_ATTR = AntalSuccess
    AGGREGATE_TYPE = Homogeneous Collection (If Possible)
    ACCUM_ATTRS_NAME = Use Attributes From One Feature
    ORDERED = No
    AGGREGATE -> FeatureMerger [REQUESTOR]
AttributeCreator_3
    ATTR_TABLE = SET_TO FeatureWR-ID = 1
    -> FeatureMerger [SUPPLIER]
FeatureMerger
    SUPPLIERS_FIRST = No
    IGNORE_NULLS = No
    ATTR_CONFLICT_RES = Use Requestor
    ATTR_ACCUM_MODE = Merge Supplier
    JOIN_KEYS = @Value(FeatureWR-ID) @Value(FeatureWR-ID) AUTO
    REJECT_NULL_MISSING_KEYS = No
    PROCESS_DUPS = No
    MERGE_TYPE = Attributes Only
    MERGED -> Sampler_5

Bookmark: För loggning
AttributeCreator_7
    ATTR_TABLE = SET_TO _FeatureIdMerger = 1
    -> FeatureMerger_6 [REQUESTOR]
FeatureMerger_6
    SUPPLIERS_FIRST = No
    IGNORE_NULLS = No
    ATTR_CONFLICT_RES = Use Requestor
    ATTR_ACCUM_MODE = Merge Supplier
    JOIN_KEYS = @Value(_FeatureIdMerger) @Value(_FeatureIdMerger) AUTO
    REJECT_NULL_MISSING_KEYS = No
    PROCESS_DUPS = No
    MERGE_TYPE = Attributes Only
    MERGED -> StringConcatenator_5

Bookmark: Kontrollera om kolumnnamn förekommer fler än en gång per dataset
Tester_2
    TEST_CLAUSE:
      TEST @Value(dl_need_new_column_name) = true
      TEST @Value(dl_new_column_name) ATTRIBUTE_HAS_VALUE ""
    BOOL_OP = AND
    TEST_DESCRIPTION = ""
    TEST_MODE = Automatic
    PASSED -> AttributeCreator
AttributeCreator
    ATTR_TABLE = SET_TO column_name = @Value(dl_new_column_name)
    -> Aggregator_2
Aggregator_2
    SEP = ,
    MODE = Geometry - Assemble One Level
    GROUP_BY = fme_feature_type_name dl_new_column_name
    COUNT_ATTR = AntalSameColumns
    AGGREGATE_TYPE = Homogeneous Collection (If Possible)
    ACCUM_ATTRS_NAME = Use Attributes From One Feature
    ORDERED = No
    AGGREGATE -> Tester_3
Tester_3
    TEST_CLAUSE = TEST @Value(AntalSameColumns) > 1
    BOOL_OP = OR
    TEST_DESCRIPTION = ""
    TEST_MODE = Automatic
    PASSED -> Aggregator_4

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    TIMEZONE = local
    INCLUDE_OFFSET = NO
    STAMP_TYPE = datetime
    -> DateTimeConverter
DateTimeConverter
    DATETIME_ATTR = _dts
    OUT_FORMAT = %Y-%m-%d %H:%M:%S
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    SRC_ATTRS = _dts
    REGEXP = YES
    NO_MATCH = _FME_NO_OP_
    -> StringReplacer_2
StringReplacer_2
    CASE = NO
    FIND_TEXT = .*\.
    SRC_ATTRS = _mils
    REGEXP = YES
    NO_MATCH = _FME_NO_OP_
    -> SubstringExtractor
SubstringExtractor
    END = 2
    SRC_STRING = @Value(_mils)
    START = 0
    RESULT_ATTR = _subMils
    -> StringConcatenator
StringConcatenator
    VAL_ATTR = _datetimestamp
    ACTION = Create New Attribute
    PARM_LINE = @Value(_dts).@Value(_subMils)
    -> AttributeRemover
AttributeRemover
    REMOVE_ATTRS = _mils,_dts,_subMils
    -> Output (output)
Output (output)
<Rejected> (output)
