FME workspace 02-lastkajen-DatalagerManage-driver - kopia.fmw

Parameters:
- FME_USER_PARAM_PRIVATE_GRP =
- FeatureListFile =
- IsWholeProcessRun =
- Manifest =
- OutputDirectory =
- ProcessModulName =
- ProcessName =
- RotDirectory =
- SchemaFlush =

Creator
    GEOMTYPE = Geometry Object
    NUM = 1
    CREATED -> ParameterFetcher_2
    CREATED -> FeatureReader [INITIATOR]
ParameterFetcher_2
    ATTR_LIST = ProcessName $(ProcessName) RotDirectory $(RotDirectory) ProcessModulName $(ProcessModulName)
    -> UUIDGenerator_2
UUIDGenerator_2
    UUID_ATTR = ProcessID
    -> FeatureReader_2 [INITIATOR]
    -> FeatureMerger_2 [SUPPLIER]
FeatureReader_2
    ATTRIBUTES = CSV,"col0,col1,col2,col3"
    ATTR_ACCUM_MODE = Only Use Result
    COMBINE_GEOM = Use Result
    CSV2_CASE_SENSITIVE_FIELD_NAMES = Yes
    CSV2_DATA_START_LINE = 1
    CSV2_DELIMITER = |
    CSV2_ENCODING = ibm437
    CSV2_ENFORCE_STRICT_SCHEMA = No
    CSV2_FEATURE_TYPE_NAME = FORMAT_NAME
    CSV2_PRESERVE_SOURCE_ENCODING = No
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = $(RotDirectory)$(ProcessName)/_schema/$(FeatureListFile)
    FORMAT = CSV2
    INTERACT = <No Spatial Filter>
    OUTPUT_FEATURES_DISPLAY = Data Features
    CSV -> FeatureMerger_2 [REQUESTOR]
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Tester
Note: Plockar bort kommentarer och tomma rader
Tester
    BOOL_OP = COMPOSITE
    COMPOSITE_TEST = "1 OR ((2 OR 3) AND (4 OR 5 OR 6) AND (7 OR 8 OR 9) AND (10 OR 11 OR 12))"
    TEST_CLAUSE:
      TEST @Value(col0) BEGINS_WITH ;
      TEST col0 ATTRIBUTE_VALUE_NULL ""
      TEST col0 ATTRIBUTE_IS_EMPTY ""
      TEST col1 ATTRIBUTE_VALUE_NULL ""
      TEST col1 ATTRIBUTE_IS_EMPTY ""
      TEST col1 ATTRIBUTE_IS_MISSING ""
      TEST col2 ATTRIBUTE_VALUE_NULL ""
      TEST col2 ATTRIBUTE_IS_EMPTY ""
      TEST col2 ATTRIBUTE_IS_MISSING ""
      TEST col3 ATTRIBUTE_VALUE_NULL ""
      TEST col3 ATTRIBUTE_IS_EMPTY ""
      TEST col3 ATTRIBUTE_IS_MISSING ""
    TEST_MODE = Automatic
    FAILED -> AttributeCreator_3
AttributeCreator_3
    ATTR_TABLE:
      SET_TO _col1_absolute_path
      SET_TO _col2_absolute_path
    -> StringSearcher_3
StringConcatenator
    ACTION = Create New Attribute
    PARM_LINE = @Value(col2)@Value(col0)
    VAL_ATTR = _get_file
    -> StringConcatenator_Output
    -> FilenamePartExtractor
StringConcatenator_Output: Inspector
FilenamePartExtractor
    DIRNAME_ATTR = _dirname
    DIRPATH_ATTR = _dirpath
    EXTENSION_ATTR = _extension
    FULLNAME_ATTR = _filename
    ROOTNAME_ATTR = _rootname
    SRC_ATTR = @Value(_get_file)
    -> StringReplacer
StringReplacer
    CASE = NO
    FIND_TEXT = FME_CONDITIONAL:DEFAULT_VALUE''BOOL_OP;OR;COMPOSITE_TEST;1;CASE_INSENSITIVE_TEST @Value(_dirpath) ENDS_WITH **\'**\'BOOL_OP;OR;COMPOSITE_TEST;1;CASE_INSENSITIVE_TEST @Value(_dirpath) ENDS_WITH **/'**/'FME_NUM_CONDITIONS3___
    NO_MATCH = _FME_NO_OP_
    REGEXP = NO
    SRC_ATTRS = _dirpath
    -> FeatureMerger [REQUESTOR]
    -> FilenamePartExtractor_Output
FilenamePartExtractor_Output: Inspector
FeatureReader
    ATTRIBUTES = schema,"filter_fme_feature_type,filter_export_column,fme_feature_type_name,column_name,dl_need_new_column_name,dl_new_column_name,dl_export,fme_data_type,native_data_type,fme_format_long_name,fme_format_short_name,_dirpath,_extension,DatasetFull,Dataset,column_name_char_length"
    ATTR_ACCUM_MODE = Only Use Result
    COMBINE_GEOM = Use Result
    DATASET = C:\dev\Datalager_procsrc\trv-lastkajen\_schema\schema-manifest.xlsx
    FORMAT = XLSXR
    INTERACT = NONE
    OUTPUT_FEATURES_DISPLAY = Schema and Data Features
    XLSXR_ALLOW_DOLLAR_SIGNS = YES
    XLSXR_CASE_SENSITIVE_FEATURE_TYPES = YES
    XLSXR_CONFIGURATION_DATASET = $(Manifest)
    XLSXR_CREATE_FEATURE_TABLES_FROM_DATA = Yes
    XLSXR_EXCEL_COL_NAMES = YES
    XLSXR_EXPAND_MERGED_CELLS = Yes
    XLSXR_FORCE_DATETIME = NO
    XLSXR_KEEP_SCHEMA_SETTINGS = YES
    XLSXR_QUERY_FEATURE_TYPES_FOR_MERGE_FILTERS = Yes
    XLSXR_READ_BLANK_AS = Missing
    XLSXR_READ_RASTER_MODE = None
    XLSXR_SCAN_SCHEMA_IF_DYNAMIC = No
    XLSXR_SCHEMA = schema,0,filter_fme_feature_type,char,17,,,1,filter_export_column,char,10,,,2,fme_feature_type_name,char,60,,,3,column_name,char,11,,,4,dl_need_new_column_name,char,6,,,5,dl_new_column_name,char,11,,,6,dl_export,char,6,,,7,fme_data_type,char,18,,,8,native_data_type,char,11,,,9,fme_format_long_name,char,15,,,10,fme_format_short_name,char,14,,,11,_dirpath,char,70,,,12,_extension,char,5,,,13,DatasetFull,char,15,,,14,Dataset,char,10,,,15,column_name_char_length,number,3," 0",,1,,,,NO,NO,1,C:\dev\Datalager_procsrc\trv-lastkajen\_schema\schema-manifest.xlsx,"0,0,15,1714",,NO,NO
    XLSXR_STRIP_SHEETNAME_SPACES = YES
    XLSXR_TABLELIST = schema
    XLSXR_TRIM_ATTR_NAME_WHITESPACE = Yes
    XLSXR_USE_SCHEMA_OTHER_FILES = No
    schema -> Tester_2
Tester_2
    BOOL_OP = OR
    COMPOSITE_TEST = 1
    TEST_CLAUSE = TEST @Value(dl_export) = true
    TEST_MODE = TEST
    PASSED -> Aggregator
Aggregator
    ACCUM_ATTRS_NAME = Drop Incoming Attributes
    GROUP_BY = _dirpath _extension fme_feature_type_name
    MODE = Attributes Only
    AGGREGATE -> Aggregator_2
Aggregator_2
    ACCUM_ATTRS_NAME = Drop Incoming Attributes
    CONCAT_ATTRS = fme_feature_type_name
    GROUP_BY = _dirpath _extension
    MODE = Attributes Only
    SEP = " "
    AGGREGATE -> FeatureMerger [SUPPLIER]
    AGGREGATE -> Aggregator_Aggregate
FeatureMerger
    ATTR_ACCUM_MODE = Merge Supplier
    ATTR_CONFLICT_RES = Use Requestor
    IGNORE_NULLS = No
    JOIN_KEYS = @Value(_dirpath) @Value(_dirpath) AUTO @Value(_extension) @Value(_extension) AUTO
    MERGE_TYPE = Attributes Only
    PROCESS_DUPS = NO
    REJECT_NULL_MISSING_KEYS = No
    SUPPLIERS_FIRST = No
    MERGED -> StringReplacer_2
    UNMERGED_REQUESTOR -> Logger
    UNUSED_SUPPLIER -> Logger
StringReplacer_2
    CASE = no
    FIND_TEXT = /
    NO_MATCH = _FME_NO_OP_
    REGEXP = YES
    REPLACE_TEXT = \
    SRC_ATTRS = _get_file
    -> StringConcatenator_2
    -> FeatureMerger_Merged
FeatureMerger_Merged: Inspector
StringConcatenator_2
    ACTION = Overwrite Existing Attributes
    ATTRLIST = _get_file
    PARM_LINE = fme_basicstring:1%17%1:"@Value(_get_file)"
    -> WorkspaceRunner
WorkspaceRunner
    BLOCKING = Yes
    WORKSPACE_FILE = $(FME_MF_DIR)02-lastkajen-DatalagerManage-main.fmw
    WORKSPACE_PARAMETERS = RotDirectory,@Value(RotDirectory),ProcessName,@Value(ProcessName),SchemaFlush,$(SchemaFlush),InData,@Value(_get_file),InData-DatabaseTable,@Value(fme_feature_type_name),OutputDirectory,$(OutputDirectory),ProcessModulName,$(ProcessModulName),IsWholeProcessRun,$(IsWholeProcessRun)
Logger
    LOG_FEATURE = LOG_ONLY
    MAXCOORDS = 20
    MAXFEATS = 20
    MESSAGE = Feature is:
    SEVERITY = INFO
Aggregator_Aggregate: Inspector

Bookmark: Absolut och relativ sökväg för col1 och col2
StringSearcher_3
    CASE = no
    REGEXP = :
    STRING_TO_SEARCH = @Value(col1)
    MATCHED -> AttributeCreator_13
    NOT_MATCHED -> Tester_13
AttributeCreator_13
    ATTR_TABLE = SET_TO _col1_absolute_path = 1
    -> StringSearcher_4
Tester_13
    BOOL_OP = OR
    TEST_CLAUSE:
      TEST col1 ATTRIBUTE_VALUE_NULL ""
      TEST col1 ATTRIBUTE_IS_EMPTY ""
      TEST col1 ATTRIBUTE_IS_MISSING ""
    TEST_MODE = Automatic
    PASSED -> StringSearcher_4
    FAILED -> StringConcatenator_13
StringConcatenator_13
    ACTION = Create New Attribute
    PARM_LINE = @Value(RotDirectory)@Value(ProcessModulName)/@Value(col1)
    VAL_ATTR = col1
    -> StringSearcher_4
StringSearcher_4
    CASE = no
    REGEXP = :
    STRING_TO_SEARCH = @Value(col2)
    MATCHED -> AttributeCreator_14
    NOT_MATCHED -> Tester_14
AttributeCreator_14
    ATTR_TABLE = SET_TO _col2_absolute_path = 1
    -> Junction
Tester_14
    BOOL_OP = OR
    TEST_CLAUSE:
      TEST col2 ATTRIBUTE_VALUE_NULL ""
      TEST col2 ATTRIBUTE_IS_EMPTY ""
      TEST col2 ATTRIBUTE_IS_MISSING ""
    TEST_MODE = Automatic
    PASSED -> Junction
    FAILED -> StringConcatenator_14
StringConcatenator_14
    ACTION = Create New Attribute
    PARM_LINE = @Value(RotDirectory)@Value(ProcessModulName)/@Value(col2)
    VAL_ATTR = col2
    -> Junction
Junction
    -> StringConcatenator
