FME workspace sks-DatalagerManage-driver.fmw

Parameters:
- FME_USER_PARAM_PRIVATE_GRP =
- FeatureListFile =
- IsWholeProcessRun =
- Manifest =
- OutputDirectory =
- PG_SCHEMA =
- ProcessModulName =
- ProcessName =
- RotDirectory =
- SchemaFlush =

Creator
    GEOMTYPE = Geometry Object
    NUM = 1
    CREATED -> FeatureReader [INITIATOR]
    CREATED -> ParameterFetcher_2
ParameterFetcher_2
    ATTR_LIST = ProcessName $(ProcessName) RotDirectory $(RotDirectory) ProcessModulName $(ProcessModulName)
    -> UUIDGenerator_2
UUIDGenerator_2
    UUID_ATTR = ProcessID
    -> FeatureReader_2 [INITIATOR]
    -> FeatureMerger_2 [SUPPLIER]
    -> StringConcatenator_8
FeatureReader_2
    ATTRIBUTES = CSV,"col0,col1,col2,col3"
    ATTR_ACCUM_MODE = Only Use Result
    COMBINE_GEOM = Use Result
    CSV2_CASE_SENSITIVE_FIELD_NAMES = Yes
    CSV2_DATA_START_LINE = 1
    CSV2_DELIMITER = |
    CSV2_ENCODING = ibm437
    CSV2_ENFORCE_STRICT_SCHEMA = No
    CSV2_FEATURE_TYPE_NAME = FORMAT_NAME
    CSV2_PRESERVE_SOURCE_ENCODING = No
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = $(RotDirectory)$(ProcessName)/_schema/$(FeatureListFile)
    FORMAT = CSV2
    INTERACT = NONE
    OUTPUT_FEATURES_DISPLAY = Data Features
    CSV -> FeatureMerger_2 [REQUESTOR]
    <REJECTED> -> Aggregator_6
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Tester
Note: Plockar bort kommentarer och tomma rader
Tester
    BOOL_OP = COMPOSITE
    COMPOSITE_TEST = 1 OR (( 2 OR 3 ) AND ( 4 OR 5 OR 6 ) AND ( 7 OR 8 OR 9 ) AND ( 10 OR 11 OR 12 ))
    TEST_CLAUSE:
      TEST @Value(col0) BEGINS_WITH ;
      TEST col0 ATTRIBUTE_VALUE_NULL ""
      TEST col0 ATTRIBUTE_IS_EMPTY ""
      TEST col1 ATTRIBUTE_VALUE_NULL ""
      TEST col1 ATTRIBUTE_IS_EMPTY ""
      TEST col1 ATTRIBUTE_IS_MISSING ""
      TEST col2 ATTRIBUTE_VALUE_NULL ""
      TEST col2 ATTRIBUTE_IS_EMPTY ""
      TEST col2 ATTRIBUTE_IS_MISSING ""
      TEST col3 ATTRIBUTE_VALUE_NULL ""
      TEST col3 ATTRIBUTE_IS_EMPTY ""
      TEST col3 ATTRIBUTE_IS_MISSING ""
    TEST_MODE = TEST
    FAILED -> AttributeCreator_3
    FAILED -> Sampler_2
AttributeCreator_3
    ATTR_TABLE:
      SET_TO _col1_absolute_path
      SET_TO _col2_absolute_path
    -> StringSearcher_3
StringConcatenator
    ACTION = Create New Attribute
    PARM_LINE = @Value(col2)@Value(col0)
    VAL_ATTR = _get_file
    -> FilenamePartExtractor
StringConcatenator_8
    ACTION = Create New Attribute
    PARM_LINE = fme_basicstring:19%7:@Value(ProcessName)_DRIVER
    VAL_ATTR = ProcessName_DRIVER
    -> FeatureMerger_3 [SUPPLIER]
    -> FeatureMerger_6 [SUPPLIER]
    -> FeatureMerger_7 [SUPPLIER]
    -> FeatureMerger_4 [SUPPLIER]
    -> FeatureMerger_8 [SUPPLIER]
    -> FeatureMerger_5 [SUPPLIER]
WorkspaceRunner
    BLOCKING = Yes
    WORKSPACE_FILE = $(FME_MF_DIR)sks-DatalagerManage-main.fmw
    WORKSPACE_PARAMETERS = RotDirectory,@Value(RotDirectory),ProcessName,@Value(ProcessName),OutputDirectory,$(OutputDirectory),ProcessModulName,$(ProcessModulName),IsWholeProcessRun,$(IsWholeProcessRun),SchemaFlush,$(SchemaFlush),PG_SCHEMA,$(PG_SCHEMA),OutSchemaFileNameSuffix,init,DestDataset_POSTGIS,PG_DATALAGER,DestDataset_POSTGIS_14,PG_DATALAGER_ADMSRV0118,InData,@Value(_get_file),InData-DatabaseTable,@Value(fme_feature_type_name)
    SUMMARY -> FeatureMerger_5 [REQUESTOR]

Bookmark: Absolut och relativ sökväg för col1 och col2
StringSearcher_3
    CASE = no
    REGEXP = :
    STRING_TO_SEARCH = @Value(col1)
    MATCHED -> AttributeCreator_13
    NOT_MATCHED -> Tester_13
AttributeCreator_13
    ATTR_TABLE = SET_TO _col1_absolute_path = 1
    -> StringSearcher_4
Tester_13
    BOOL_OP = OR
    COMPOSITE_TEST = 1 OR 2 OR 3
    TEST_CLAUSE:
      TEST col1 ATTRIBUTE_VALUE_NULL ""
      TEST col1 ATTRIBUTE_IS_EMPTY ""
      TEST col1 ATTRIBUTE_IS_MISSING ""
    TEST_MODE = TEST
    PASSED -> StringSearcher_4
    FAILED -> StringConcatenator_13
StringConcatenator_13
    ACTION = Create New Attribute
    PARM_LINE = @Value(RotDirectory)@Value(ProcessModulName)/@Value(col1)
    VAL_ATTR = col1
    -> StringSearcher_4
StringSearcher_4
    CASE = no
    REGEXP = :
    STRING_TO_SEARCH = @Value(col2)
    MATCHED -> AttributeCreator_14
    NOT_MATCHED -> Tester_14
AttributeCreator_14
    ATTR_TABLE = SET_TO _col2_absolute_path = 1
    -> Junction
Tester_14
    BOOL_OP = OR
    COMPOSITE_TEST = 1 OR 2 OR 3
    TEST_CLAUSE:
      TEST col2 ATTRIBUTE_VALUE_NULL ""
      TEST col2 ATTRIBUTE_IS_EMPTY ""
      TEST col2 ATTRIBUTE_IS_MISSING ""
    TEST_MODE = TEST
    PASSED -> Junction
    FAILED -> StringConcatenator_14
StringConcatenator_14
    ACTION = Create New Attribute
    PARM_LINE = @Value(RotDirectory)@Value(ProcessModulName)/@Value(col2)
    VAL_ATTR = col2
    -> Junction
Junction
    -> StringConcatenator

Bookmark: För att plocka ut de olika dataseten/tabellerna från en databasbaserad datakälla som ex. GeoPackage
FilenamePartExtractor
    DIRNAME_ATTR = _dirname
    DIRPATH_ATTR = _dirpath
    EXTENSION_ATTR = _extension
    FULLNAME_ATTR = _filename
    ROOTNAME_ATTR = _rootname
    SRC_ATTR = @Value(_get_file)
    -> StringReplacer
StringReplacer
    CASE = NO
    FIND_TEXT = FME_CONDITIONAL:DEFAULT_VALUE''BOOL_OP;OR;COMPOSITE_TEST;1;CASE_INSENSITIVE_TEST @Value(_dirpath) ENDS_WITH **\'**\'BOOL_OP;OR;COMPOSITE_TEST;1;CASE_INSENSITIVE_TEST @Value(_dirpath) ENDS_WITH **/'**/'FME_NUM_CONDITIONS3___
    NO_MATCH = _FME_NO_OP_
    REGEXP = NO
    SRC_ATTRS = _dirpath
    -> FeatureMerger [REQUESTOR]
FeatureReader
    ATTRIBUTES = schema,"filter_fme_feature_type,filter_export_column,fme_feature_type_name,column_name,dl_need_new_column_name,dl_new_column_name,dl_export,fme_data_type,native_data_type,fme_format_long_name,fme_format_short_name,_dirpath,_extension,DatasetFull,Dataset,column_name_char_length"
    ATTR_ACCUM_MODE = Only Use Result
    COMBINE_GEOM = Use Result
    DATASET = $(Manifest)
    FORMAT = XLSXR
    INTERACT = NONE
    OUTPUT_FEATURES_DISPLAY = Schema and Data Features
    XLSXR_ALLOW_DOLLAR_SIGNS = YES
    XLSXR_CASE_SENSITIVE_FEATURE_TYPES = YES
    XLSXR_CONFIGURATION_DATASET = $(Manifest)
    XLSXR_CREATE_FEATURE_TABLES_FROM_DATA = Yes
    XLSXR_EXCEL_COL_NAMES = YES
    XLSXR_EXPAND_MERGED_CELLS = Yes
    XLSXR_FORCE_DATETIME = NO
    XLSXR_KEEP_SCHEMA_SETTINGS = YES
    XLSXR_QUERY_FEATURE_TYPES_FOR_MERGE_FILTERS = Yes
    XLSXR_READ_BLANK_AS = Missing
    XLSXR_READ_RASTER_MODE = None
    XLSXR_SCAN_SCHEMA_IF_DYNAMIC = No
    XLSXR_SCHEMA = schema,0,filter_fme_feature_type,char,17,,,1,filter_export_column,char,10,,,2,fme_feature_type_name,char,60,,,3,column_name,char,11,,,4,dl_need_new_column_name,char,6,,,5,dl_new_column_name,char,11,,,6,dl_export,char,6,,,7,fme_data_type,char,18,,,8,native_data_type,char,11,,,9,fme_format_long_name,char,15,,,10,fme_format_short_name,char,14,,,11,_dirpath,char,70,,,12,_extension,char,5,,,13,DatasetFull,char,15,,,14,Dataset,char,10,,,15,column_name_char_length,number,3," 0",,1,,,,NO,NO,1,$(Manifest),"0,0,15,1714",,NO,NO
    XLSXR_STRIP_SHEETNAME_SPACES = YES
    XLSXR_TABLELIST = schema
    XLSXR_TRIM_ATTR_NAME_WHITESPACE = Yes
    XLSXR_USE_SCHEMA_OTHER_FILES = No
    schema -> Tester_2
    <REJECTED> -> Aggregator_7
Tester_2
    BOOL_OP = OR
    COMPOSITE_TEST = 1
    TEST_CLAUSE = TEST @Value(dl_export) = true
    TEST_MODE = TEST
    PASSED -> Aggregator
Aggregator
    ACCUM_ATTRS_NAME = Drop Incoming Attributes
    GROUP_BY = _dirpath _extension fme_feature_type_name
    MODE = Attributes Only
    AGGREGATE -> Aggregator_2
Aggregator_2
    ACCUM_ATTRS_NAME = Drop Incoming Attributes
    CONCAT_ATTRS = fme_feature_type_name
    GROUP_BY = _dirpath _extension
    MODE = Attributes Only
    SEP = " "
    AGGREGATE -> FeatureMerger [SUPPLIER]
FeatureMerger
    ATTR_ACCUM_MODE = Merge Supplier
    ATTR_CONFLICT_RES = Use Requestor
    IGNORE_NULLS = No
    JOIN_KEYS = @Value(_dirpath) @Value(_dirpath) AUTO @Value(_extension) @Value(_extension) AUTO
    MERGE_TYPE = Attributes Only
    PROCESS_DUPS = NO
    REJECT_NULL_MISSING_KEYS = No
    SUPPLIERS_FIRST = No
    MERGED -> WorkspaceRunner
    UNMERGED_REQUESTOR -> Aggregator_8
    <REJECTED> -> Aggregator_3

Bookmark: Loggning
Note: Endast till för som signal att starta logg
Sampler_2
    RATE = 1
    SAMPLE_MODE = No
    SAMPLE_TYPE_LONG = First N Features
    SAMPLED -> FeatureMerger_3 [REQUESTOR]
Aggregator_6
    ACCUM_ATTRS_NAME = Use Attributes From One Feature
    AGGREGATE_TYPE = Homogeneous Collection (If Possible)
    GROUP_BY = _reader_error
    MODE = Geometry - Assemble One Level
    SEP = ", "
    AGGREGATE -> AttributeCreator
AttributeCreator
    ATTR_TABLE = SET_TO _FileToRead = $(RotDirectory)$(ProcessName)/_schema/$(FeatureListFile)
    -> FeatureMerger_6 [REQUESTOR]
FeatureMerger_6
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_10
StringConcatenator_10
    ACTION = Create New Attribute
    PARM_LINE:
      fme_basicstring:15%19%14%1%14%1%21:Läsning av fil @Value(_FileToRead) misslyckades.
      Felmeddelande:
      @Value(_reader_error)
    VAL_ATTR = Logg
    -> DTStamperYYYY-MM-DD_HH:MI:SS.sss_2
DTStamperYYYY-MM-DD_HH:MI:SS.sss_2
    -> Logg_5
Logg_5: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_3
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_3
StringConcatenator_3
    ACTION = Create New Attribute
    PARM_LINE = fme_basicstring:4%26%13%11%18:Kör @Value(ProcessName_DRIVER) för data i "$(Manifest)" till datalagret.
    VAL_ATTR = Logg
    -> DTStamperYYYY-MM-DD_HH:MI:SS.sss
DTStamperYYYY-MM-DD_HH:MI:SS.sss
    -> Logg_2
Logg_2: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,INFORMATION,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_5
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_9
StringConcatenator_9
    ACTION = Create New Attribute
    PARM_LINE = fme_basicstring:26%14%19%55:@Value(ProcessName_DRIVER) avslutad med @Value(_proc_count) st. objekt från _modul-settings-dataset.ini hanterade.
    VAL_ATTR = Logg
    -> DTStamperYYYY-MM-DD_HH:MI:SS.sss_4
DTStamperYYYY-MM-DD_HH:MI:SS.sss_4
    -> Logg_4
Logg_4: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,KLART,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Aggregator_8
    ACCUM_ATTRS_NAME = Use Attributes From One Feature
    AGGREGATE_TYPE = Homogeneous Collection (If Possible)
    GROUP_BY = _dirpath
    MODE = Geometry - Assemble One Level
    SEP = ", "
    AGGREGATE -> Aggregator_9
Aggregator_9
    ACCUM_ATTRS_NAME = Use Attributes From One Feature
    AGGREGATE_TYPE = Homogeneous Collection (If Possible)
    CONCAT_ATTRS = _dirpath
    MODE = Geometry - Assemble One Level
    SEP = ", "
    AGGREGATE -> FeatureMerger_8 [REQUESTOR]
FeatureMerger_8
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_6
StringConcatenator_6
    ACTION = Create New Attribute
    PARM_LINE:
      fme_basicstring:84%1%8%1%16:Motsvarande dataset i schemamanifest saknas för innehåll _modul-settings-dataset.ini
      Berörda:
      @Value(_dirpath)
    VAL_ATTR = Logg
    -> DTStamperYYYY-MM-DD_HH:MI:SS.sss_6
DTStamperYYYY-MM-DD_HH:MI:SS.sss_6
    -> Logg_7
Logg_7: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,VARNING,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Aggregator_3
    ACCUM_ATTRS_NAME = Use Attributes From One Feature
    AGGREGATE_TYPE = Homogeneous Collection (If Possible)
    GROUP_BY = fme_rejection_code
    MODE = Geometry - Assemble One Level
    SEP = ", "
    AGGREGATE -> Aggregator_4
Aggregator_4
    ACCUM_ATTRS_NAME = Use Attributes From One Feature
    AGGREGATE_TYPE = Homogeneous Collection (If Possible)
    CONCAT_ATTRS = fme_rejection_code
    MODE = Geometry - Assemble One Level
    SEP = ", "
    AGGREGATE -> FeatureMerger_4 [REQUESTOR]
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_4
StringConcatenator_4
    ACTION = Create New Attribute
    PARM_LINE:
      fme_basicstring:87%1%14%1%26:Innehåll i _modul-settings-dataset.ini kunde inte länkas mot schemamanifest för dataset
      Felmeddelande:
      @Value(fme_rejection_code)
    VAL_ATTR = Logg
    -> DTStamperYYYY-MM-DD_HH:MI:SS.sss_3
DTStamperYYYY-MM-DD_HH:MI:SS.sss_3
    -> Logg_3
Logg_3: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Aggregator_7
    ACCUM_ATTRS_NAME = Use Attributes From One Feature
    AGGREGATE_TYPE = Homogeneous Collection (If Possible)
    GROUP_BY = _reader_error
    MODE = Geometry - Assemble One Level
    SEP = ", "
    AGGREGATE -> AttributeCreator_2
AttributeCreator_2
    ATTR_TABLE = SET_TO _FileToRead = $(Manifest)
    -> FeatureMerger_7 [REQUESTOR]
FeatureMerger_7
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_5
StringConcatenator_5
    ACTION = Create New Attribute
    PARM_LINE:
      fme_basicstring:15%19%14%1%14%1%21:Läsning av fil @Value(_FileToRead) misslyckades.
      Felmeddelande:
      @Value(_reader_error)
    VAL_ATTR = Logg
    -> DTStamperYYYY-MM-DD_HH:MI:SS.sss_5
DTStamperYYYY-MM-DD_HH:MI:SS.sss_5
    -> Logg_6
Logg_6: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    INCLUDE_OFFSET = NO
    STAMP_TYPE = datetime
    TIMEZONE = local
    -> DateTimeConverter
DateTimeConverter
    DATETIME_ATTR = _dts
    OUT_FORMAT = %Y-%m-%d %H:%M:%S
    PASSTHROUGH = NO
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    NO_MATCH = _FME_NO_OP_
    REGEXP = YES
    SRC_ATTRS = _dts
    -> StringReplacer_2
StringReplacer_2
    CASE = NO
    FIND_TEXT = .*\.
    NO_MATCH = _FME_NO_OP_
    REGEXP = YES
    SRC_ATTRS = _mils
    -> SubstringExtractor
SubstringExtractor
    END = 2
    RESULT_ATTR = _subMils
    SRC_STRING = @Value(_mils)
    START = 0
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)
