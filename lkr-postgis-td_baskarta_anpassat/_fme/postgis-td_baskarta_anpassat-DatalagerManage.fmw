FME workspace postgis-td_baskarta_anpassat-DatalagerManage.fmw

Parameters:
- DestDataset_POSTGIS =
- DestDataset_POSTGIS_13 =
- DestDataset_POSTGIS_14 =
- DestDataset_POSTGIS_15 =
- FME_USER_PARAM_PRIVATE_GRP =
- IsWholeProcessRun =
- Manifest =
- OutSchemaFileExtention =
- OutSchemaFileName =
- OutSchemaFileNameSuffix =
- OutputDirectory =
- PG_SCHEMA =
- ProcessModulName =
- ProcessName =
- RotDirectory =
- SchemaFlush =

Readers:
- XLSXR_1: XLSXR from $(SchemaFlush)
- SCHEMA_FROM_TABLE_1: SCHEMA_FROM_TABLE from $(Manifest)

Writers:
- SDF3_1: SDF3 to $(OutputDirectory) in EPSG:3008
- SHAPEFILE_1: SHAPEFILE to $(OutputDirectory) in EPSG:3008
- POSTGIS_1: POSTGIS to $(DestDataset_POSTGIS) in EPSG:3008
- POSTGIS_2: POSTGIS to $(DestDataset_POSTGIS) in EPSG:3008
- POSTGIS_3: POSTGIS to $(DestDataset_POSTGIS) in EPSG:3008
- POSTGIS_4: POSTGIS to $(DestDataset_POSTGIS) in EPSG:3008
- POSTGIS_5: POSTGIS to $(DestDataset_POSTGIS) in EPSG:3008
- POSTGIS_11: POSTGIS to $(DestDataset_POSTGIS_15) in EPSG:3008
- POSTGIS_6: POSTGIS to $(DestDataset_POSTGIS_13) in EPSG:3008
- POSTGIS_7: POSTGIS to $(DestDataset_POSTGIS_13) in EPSG:3008
- POSTGIS_8: POSTGIS to $(DestDataset_POSTGIS_13) in EPSG:3008
- POSTGIS_9: POSTGIS to $(DestDataset_POSTGIS_13) in EPSG:3008
- POSTGIS_10: POSTGIS to $(DestDataset_POSTGIS_13) in EPSG:3008
- POSTGIS_12: POSTGIS to $(DestDataset_POSTGIS_14) in EPSG:3008

Creator
    GEOMTYPE = Geometry Object
    NUM = 1
    CREATED -> ParameterFetcher_2
ParameterFetcher_2
    ATTR_LIST = ProcessName $(ProcessName) RotDirectory $(RotDirectory)
    -> UUIDGenerator_2
UUIDGenerator_2
    UUID_ATTR = ProcessID
    -> AttributeCreator_12
AttributeCreator_12
    ATTR_TABLE = SET_TO _FeatureIdMerger = 1
    -> AttributeCreator_12_OUTPUT_-__FeatureMerger_3_SUPPLIER
AttributeCreator_12_OUTPUT_-__FeatureMerger_3_SUPPLIER: Junction
    -> Junction
    -> Junction_3
    -> Junction_7
    -> Junction_9
    -> Junction_13
    -> Junction_14
Note: FeatureMerger_2 : Supplier
Junction
    -> Junction_2
Note: FeatureMerger_3 : Supplier
Junction_3
    -> Junction_4
Note: Junction_12 : Input
Junction_13
Note: FeatureMerger_5 : Supplier
Junction_7
    -> Junction_8
Note: FeatureMerger_6 : Supplier
Junction_9
    -> Junction_10
Note: Junction_6 : Input
Junction_14
    -> Junction_15
Note: Parametrar / * [RotDirectory] Kommer från batch-processen och är obligatoriskt för alla FME-processor. / * [ProcessName] Kommer från batch-processen och är obligatoriskt för alla FME-processor. / * [Manifest] Excel-fil från ett tidigare exporterat schema anpassad med nya kolumnnamn samt vilken data som ska exporteras. / * [OutputDirectory] Katalogsökväg för exporterad geodata (delrepository).
schema (reader XLSXR_1)
    attributes: fme_feature_type_name char(20), column_name char(16), dl_need_new_column_name char(6), dl_new_column_name char(12), dl_export char(5), fme_data_type char(18), native_data_type char(14), fme_format_long_name char(22), fme_format_short_name char(15), _dirpath char(1), _extension char(1), DatasetFull char(8), Dataset char(8), column_name_char_length number(3,0)
    -> Tester_4
Tester_4
    BOOL_OP = OR
    TEST_CLAUSE = TEST @Value(dl_export) = true
    TEST_MODE = TEST
    PASSED -> Tester_2
    PASSED -> Aggregator_3
    PASSED -> Sampler_2
Aggregator_3
    ACCUM_ATTRS_NAME = Drop Incoming Attributes
    AGGREGATE_TYPE = Homogeneous Collection (If Possible)
    GROUP_BY = fme_feature_type_name fme_format_short_name Dataset
    MODE = Geometry - Assemble One Level
    ORDERED = No
    SEP = ,
    AGGREGATE -> StringConcatenator
StringConcatenator
    ACTION = Create New Attribute
    PARM_LINE = @Value(fme_feature_type_name)
    VAL_ATTR = _filterValue
    -> StringCaseChanger
StringCaseChanger
    ATTRCHOICE = Selected Attributes
    ATTRLIST = _filterValue
    CHANGE_TYPE = lowercase
    -> TestFilter_2
TestFilter_2
    DEFAULT_VALUE = <UNFILTERED>
    TEST_LIST = "BOOL_OP,OR,COMPOSITE_TEST,""""""<Unused>"""""",TEST_CLAUSE,TEST @Value(_filterValue) = td_baskarta.gs_stompunkt_p",td_baskarta.gs_stompunkt_p,"BOOL_OP,OR,COMPOSITE_TEST,""""""<Unused>"""""",TEST_CLAUSE,TEST @Value(_filterValue) = td_baskarta.gs_stompunkt_p_ism_ap",td_baskarta.gs_stompunkt_p_ism_ap,"BOOL_OP,OR,COMPOSITE_TEST,""""""<Unused>"""""",TEST_CLAUSE,TEST @Value(_filterValue) = td_baskarta.ho_hojddjuppunkt_p",td_baskarta.ho_hojddjuppunkt_p,"BOOL_OP,OR,COMPOSITE_TEST,""""""<Unused>"""""",TEST_CLAUSE,TEST @Value(_filterValue) = td_baskarta.ho_hojddjuppunkt_p_ism_ap",td_baskarta.ho_hojddjuppunkt_p_ism_ap,"BOOL_OP,OR,COMPOSITE_TEST,""""""<Unused>"""""",TEST_CLAUSE,TEST @Value(_filterValue) = td_baskarta.ma_markanvandningyta_y",td_baskarta.ma_markanvandningyta_y,"BOOL_OP,OR,COMPOSITE_TEST,""""""<Unused>"""""",TEST_CLAUSE,TEST @Value(_filterValue) = td_baskarta.ma_markanvandningyta_y_ism_ap",td_baskarta.ma_markanvandningyta_y_ism_ap,"BOOL_OP,OR,COMPOSITE_TEST,""""""1"""""",TEST_CLAUSE,TEST @Value(_filterValue) = td_baskarta.md_markdetalj_l",td_baskarta.md_markdetalj_l,"BOOL_OP,OR,COMPOSITE_TEST,""""""1"""""",TEST_CLAUSE,TEST @Value(_filterValue) = td_baskarta.md_markdetalj_l_ism_ap",td_baskarta.md_markdetalj_l_ism_ap,"BOOL_OP,OR,COMPOSITE_TEST,""""""<Unused>"""""",TEST_CLAUSE,TEST @Value(_filterValue) = td_baskarta.ml_markdetalj_l",td_baskarta.ml_markdetalj_l,"BOOL_OP,OR,COMPOSITE_TEST,""""""<Unused>"""""",TEST_CLAUSE,TEST @Value(_filterValue) = td_baskarta.ml_markdetalj_l_ism_ap",td_baskarta.ml_markdetalj_l_ism_ap,"BOOL_OP,OR,COMPOSITE_TEST,""""""<Unused>"""""",TEST_CLAUSE,TEST @Value(_filterValue) = td_baskarta.td_namn_p",td_baskarta.td_namn_p,"BOOL_OP,OR,COMPOSITE_TEST,""""""<Unused>"""""",TEST_CLAUSE,TEST @Value(_filterValue) = td_baskarta.td_namn_p_ism_ap",td_baskarta.td_namn_p_ism_ap
    td_baskarta.gs_stompunkt_p -> FeatureReader [INITIATOR]
    td_baskarta.gs_stompunkt_p_ism_ap -> FeatureReader_2 [INITIATOR]
    td_baskarta.ho_hojddjuppunkt_p -> FeatureReader_3 [INITIATOR]
    td_baskarta.ho_hojddjuppunkt_p_ism_ap -> FeatureReader_4 [INITIATOR]
    td_baskarta.ma_markanvandningyta_y -> FeatureReader_5 [INITIATOR]
    td_baskarta.ma_markanvandningyta_y_ism_ap -> FeatureReader_6 [INITIATOR]
    td_baskarta.ml_markdetalj_l -> FeatureReader_7 [INITIATOR]
    td_baskarta.ml_markdetalj_l_ism_ap -> FeatureReader_8 [INITIATOR]
    td_baskarta.td_namn_p -> FeatureReader_9 [INITIATOR]
    td_baskarta.td_namn_p_ism_ap -> FeatureReader_10 [INITIATOR]
    td_baskarta.md_markdetalj_l -> FeatureReader_11 [INITIATOR]
    td_baskarta.md_markdetalj_l_ism_ap -> FeatureReader_12 [INITIATOR]
FeatureReader
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_2
    <REJECTED> -> Junction_5
AttributeExposer_2
    ATTR_LIST = td_id,gs_stompunktid,gs_stompunkttyp,gs_kategori,gs_nattyp,ex_status,ex_pp_geodimeternat,ex_pp_hbg,ex_pp_lm,ex_pp_rh2000,ex_pp_rh2000_initial,ex_pp_rix95,ex_pp_skan95,ex_sweref99,ex_ppnr_lm,ex_z_s68,ex_ma_link
    -> Tester
Tester
    BOOL_OP = OR
    TEST_CLAUSE = TEST gs_stompunktid ATTRIBUTE_HAS_A_VALUE ""
    TEST_MODE = TEST
    PASSED -> FeatureMerger [SUPPLIER]
FeatureReader_2
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_3
    <REJECTED> -> Junction_5
AttributeExposer_3
    ATTR_LIST = obj_id
    -> FeatureMerger [REQUESTOR]
FeatureMerger
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> vektor2vinklar
    <REJECTED> -> Junction_11
FeatureReader_3
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_4
    <REJECTED> -> Junction_5
AttributeExposer_4
    ATTR_LIST = td_id,td_ho_verksamhet_1,ho_hardgjordyta,ho_classification,ho_propertyvalue
    -> Tester_5
Tester_5
    BOOL_OP = OR
    TEST_CLAUSE = TEST ho_propertyvalue ATTRIBUTE_HAS_A_VALUE ""
    TEST_MODE = TEST
    PASSED -> FeatureMerger_7 [SUPPLIER]
FeatureReader_4
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_5
    <REJECTED> -> Junction_5
AttributeExposer_5
    ATTR_LIST = obj_id
    -> FeatureMerger_7 [REQUESTOR]
FeatureMerger_7
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> vektor2vinklar
    <REJECTED> -> Junction_11
FeatureReader_5
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_6
    <REJECTED> -> Junction_5
AttributeExposer_6
    ATTR_LIST = td_id,ma_markanvandningtyp,td_ma_verksamhet_1,td_ma_verksamhet_2,td_notering_text_1
    -> Tester_6
Tester_6
    BOOL_OP = OR
    TEST_CLAUSE = TEST td_notering_text_1 ATTRIBUTE_HAS_A_VALUE ""
    TEST_MODE = TEST
    PASSED -> FeatureMerger_8 [SUPPLIER]
FeatureReader_6
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_7
    <REJECTED> -> Junction_5
AttributeExposer_7
    ATTR_LIST = obj_id
    -> FeatureMerger_8 [REQUESTOR]
FeatureMerger_8
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> vektor2vinklar
    <REJECTED> -> Junction_11
FeatureReader_11
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_12
    <REJECTED> -> Junction_5
AttributeExposer_12
    ATTR_LIST = td_id,md_markdetaljtyp,td_md_verksamhet_1,td_md_verksamhet_2,md_marklinje,md_planlagetyp,td_notering_text_1
    -> Tester_9
Tester_9
    BOOL_OP = OR
    TEST_CLAUSE = TEST td_notering_text_1 ATTRIBUTE_HAS_A_VALUE ""
    TEST_MODE = TEST
    PASSED -> FeatureMerger_11 [SUPPLIER]
FeatureReader_12
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_13
    <REJECTED> -> Junction_5
AttributeExposer_13
    ATTR_LIST = obj_id
    -> FeatureMerger_11 [REQUESTOR]
FeatureMerger_11
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> vektor2vinklar
    <REJECTED> -> Junction_11
FeatureReader_7
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_8
    <REJECTED> -> Junction_5
AttributeExposer_8
    ATTR_LIST = td_id,ml_markdetaljtyp,td_ml_verksamhet_1,td_ml_verksamhet_2,ml_marklinje,ml_planlagetyp,td_notering_text_1
    -> Tester_7
Tester_7
    BOOL_OP = OR
    TEST_CLAUSE = TEST td_notering_text_1 ATTRIBUTE_HAS_A_VALUE ""
    TEST_MODE = TEST
    PASSED -> FeatureMerger_9 [SUPPLIER]
FeatureReader_8
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_9
    <REJECTED> -> Junction_5
AttributeExposer_9
    ATTR_LIST = obj_id
    -> FeatureMerger_9 [REQUESTOR]
FeatureMerger_9
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> vektor2vinklar
    <REJECTED> -> Junction_11
FeatureReader_9
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_10
    <REJECTED> -> Junction_5
AttributeExposer_10
    ATTR_LIST = td_id,td_namntyp,td_verksamhet_1,td_verksamhet_2,td_namn_1
    -> Tester_8
Tester_8
    BOOL_OP = OR
    TEST_CLAUSE = TEST td_namn_1 ATTRIBUTE_HAS_A_VALUE ""
    TEST_MODE = TEST
    PASSED -> FeatureMerger_10 [SUPPLIER]
FeatureReader_10
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_11
    <REJECTED> -> Junction_5
AttributeExposer_11
    ATTR_LIST = obj_id
    -> FeatureMerger_10 [REQUESTOR]
FeatureMerger_10
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> vektor2vinklar
    <REJECTED> -> Junction_11
vektor2vinklar
    -> ArcStroker
Note: ArcStroker [ArcStroker] / General: / Stroke By: Maximum Deviation / Maximum Deviation: 0.02 / Make Polygon Out of 360 Degree Arcs: No
ArcStroker
    MAKE_POLY = No
    STROKE_CHOICE = Maximum Deviation
    TOLERANCE_VAL = 0.02
    STROKED -> 2DForcer
2DForcer
    2D -> GeometryRefiner
GeometryRefiner
    -> AttributeExposer
AttributeExposer
    ATTR_LIST = fme_feature_type
    -> AttributeCopier
AttributeCopier
    ATTR_TABLE = COPY fme_feature_type > _name
    -> StringReplacer
StringReplacer
    CASE = NO
    FIND_TEXT = (_p|_l|_y|_t)$
    NO_MATCH = _FME_NO_OP_
    REGEXP = YES
    SRC_ATTRS = _name
    -> StringReplacer_2
StringReplacer_2
    CASE = NO
    FIND_TEXT = ^td_baskarta.
    NO_MATCH = _FME_NO_OP_
    REGEXP = YES
    SRC_ATTRS = _name
    -> AttributeCreator_5
AttributeCreator_5
    ATTR_TABLE = SET_TO _name_extension
    -> StringConcatenator_4
StringConcatenator_4
    ACTION = Create New Attribute
    PARM_LINE = @Value(_name)@Value(_name_extension)_p
    VAL_ATTR = DatasetName
    -> TestFilter
TestFilter
    DEFAULT_VALUE = <UNFILTERED>
    TEST_LIST = "BOOL_OP,OR,COMPOSITE_TEST,""""""<Unused>"""""",TEST_CLAUSE,TEST @Value(DatasetName) = gs_stompunkt_p_ism_ap_p",gs_stompunkt_p_ism_ap_p,"BOOL_OP,OR,COMPOSITE_TEST,""""""<Unused>"""""",TEST_CLAUSE,TEST @Value(DatasetName) = ho_hojddjuppunkt_p_ism_ap_p",ho_hojddjuppunkt_p_ism_ap_p,"BOOL_OP,OR,COMPOSITE_TEST,""""""<Unused>"""""",TEST_CLAUSE,TEST @Value(DatasetName) = ma_markanvandningyta_y_ism_ap_p",ma_markanvandningyta_y_ism_ap_p,"BOOL_OP,OR,COMPOSITE_TEST,""""""1"""""",TEST_CLAUSE,TEST @Value(DatasetName) = md_markdetalj_l_ism_ap_p",md_markdetalj_l_ism_ap_p,"BOOL_OP,OR,COMPOSITE_TEST,""""""<Unused>"""""",TEST_CLAUSE,TEST @Value(DatasetName) = ml_markdetalj_l_ism_ap_p",ml_markdetalj_l_ism_ap_p,"BOOL_OP,OR,COMPOSITE_TEST,""""""<Unused>"""""",TEST_CLAUSE,TEST @Value(DatasetName) = td_namn_p_ism_ap_p",td_namn_p_ism_ap_p
    gs_stompunkt_p_ism_ap_p -> AttributeKeeper
    ho_hojddjuppunkt_p_ism_ap_p -> AttributeKeeper_2
    ma_markanvandningyta_y_ism_ap_p -> AttributeKeeper_3
    ml_markdetalj_l_ism_ap_p -> AttributeKeeper_4
    td_namn_p_ism_ap_p -> AttributeKeeper_5
    md_markdetalj_l_ism_ap_p -> AttributeKeeper_6
AttributeKeeper
    CREATE_BULK_MODE_FEATURES = No
    KEEP_ATTRS = DatasetName,gs_kategori,ex_pp_skan95,ex_z_s68,radianer,ex_ppnr_lm,gs_nattyp,gs_stompunkttyp,ex_pp_lm,ex_pp_hbg,ex_pp_rh2000,ex_pp_rix95,ex_sweref99,ex_pp_geodimeternat,ex_ma_link,gon,gs_stompunktid,ex_status,ex_pp_rh2000_initial,grader
    -> AttributeManager
    -> Junction_12
    -> fastighet_y (writer SDF3_1)
    -> schema (writer POSTGIS_1)
    -> Table1 (writer POSTGIS_6)
AttributeManager
    ATTR_TABLE:
      RENAME_SET_VALUE gs_stompunktid > gs_pktid
      RENAME_SET_VALUE gs_stompunkttyp > gs_pkttyp
      RENAME_SET_VALUE gs_kategori > gs_kategor
      RENAME_SET_VALUE ex_status > status
      RENAME_SET_VALUE ex_pp_geodimeternat > pp_geonat
      RENAME_SET_VALUE ex_pp_hbg > pp_hbg
      RENAME_SET_VALUE ex_pp_lm > pp_lm
      RENAME_SET_VALUE ex_pp_rh2000 > pprh2k
      RENAME_SET_VALUE ex_pp_rh2000_initial > pprh2kinit
      RENAME_SET_VALUE ex_pp_rix95 > pp_rix95
      RENAME_SET_VALUE ex_pp_skan95 > pp_skan95
      RENAME_SET_VALUE ex_sweref99 > swe99
      RENAME_SET_VALUE ex_ppnr_lm > ppnr_lm
      RENAME_SET_VALUE ex_z_s68 > z_s68
      RENAME_SET_VALUE ex_ma_link > ma_link
    -> Shapefile1 (writer SHAPEFILE_1)
Note: <@Value(DatasetName)>: [SHAPEFILE]
Shapefile1 (writer SHAPEFILE_1)
    attributes: gs_pktid char(200), gs_pkttyp char(200), gs_kategor char(200), gs_nattyp char(200), status char(200), pp_geonat char(200), pp_hbg char(200), pp_lm char(200), pprh2k char(200), pprh2kinit char(200), pp_rix95 char(200), pp_skan95 char(200), swe99 char(200), ppnr_lm char(200), z_s68 char(200), ma_link char(200), radianer double, grader double, gon double
Note: <@Value(DatasetName)>: PG_DATALAGER [POSTGIS] - 1
schema (writer POSTGIS_1)
    attributes: gs_stompunktid varchar(200), gs_stompunkttyp varchar(200), gs_kategori varchar(200), gs_nattyp varchar(200), ex_status varchar(200), ex_pp_geodimeternat varchar(200), ex_pp_hbg varchar(200), ex_pp_lm varchar(200), ex_pp_rh2000 varchar(200), ex_pp_rh2000_initial varchar(200), ex_pp_rix95 varchar(200), ex_pp_skan95 varchar(200), ex_sweref99 varchar(200), ex_ppnr_lm varchar(200), ex_z_s68 varchar(200), ex_ma_link varchar(200), radianer float8, grader float8, gon float8
Note: <@Value(DatasetName)>: [SDF3]
fastighet_y (writer SDF3_1)
    attributes: gs_stompunktid char(200), gs_stompunkttyp char(200), gs_kategori char(200), gs_nattyp char(200), ex_status char(200), ex_pp_geodimeternat char(200), ex_pp_hbg char(200), ex_pp_lm char(200), ex_pp_rh2000 char(200), ex_pp_rh2000_initial char(200), ex_pp_rix95 char(200), ex_pp_skan95 char(200), ex_sweref99 char(200), ex_ppnr_lm char(200), ex_z_s68 char(200), ex_ma_link char(200), radianer char(200), grader char(200), gon char(200)
Note: <@Value(DatasetName)>: PG_DATALAGER_ADMSRV0118 [POSTGIS] - 1
Table1 (writer POSTGIS_6)
    attributes: gs_stompunktid varchar(200), gs_stompunkttyp varchar(200), gs_kategori varchar(200), gs_nattyp varchar(200), ex_status varchar(200), ex_pp_geodimeternat varchar(200), ex_pp_hbg varchar(200), ex_pp_lm varchar(200), ex_pp_rh2000 varchar(200), ex_pp_rh2000_initial varchar(200), ex_pp_rix95 varchar(200), ex_pp_skan95 varchar(200), ex_sweref99 varchar(200), ex_ppnr_lm varchar(200), ex_z_s68 varchar(200), ex_ma_link varchar(200), radianer float8, grader float8, gon float8
AttributeKeeper_2
    CREATE_BULK_MODE_FEATURES = No
    KEEP_ATTRS = ho_classification,gon,radianer,grader,ho_propertyvalue,DatasetName,ho_hardgjordyta,td_ho_verksamhet_1
    -> Junction_12
    -> AttributeManager_2
    -> fastighet_y00 (writer SDF3_1)
    -> Table1 (writer POSTGIS_2)
    -> Table1 (writer POSTGIS_7)
AttributeManager_2
    ATTR_TABLE:
      RENAME_SET_VALUE td_ho_verksamhet_1 > td_ho_v_1
      RENAME_SET_VALUE ho_hardgjordyta > ho_hardyta
      RENAME_SET_VALUE ho_classification > ho_class
      RENAME_SET_VALUE ho_propertyvalue > ho_propval
    -> Shapefile100 (writer SHAPEFILE_1)
Note: <@Value(DatasetName)>: [SHAPEFILE]
Shapefile100 (writer SHAPEFILE_1)
    attributes: td_ho_v_1 char(200), ho_hardyta char(200), ho_class char(200), ho_propval char(200), radianer double, grader double, gon double
Note: <@Value(DatasetName)>: PG_DATALAGER [POSTGIS] - 2
Table1 (writer POSTGIS_2)
    attributes: td_ho_verksamhet_1 varchar(200), ho_hardgjordyta varchar(200), ho_classification varchar(200), ho_propertyvalue varchar(200), radianer float8, grader float8, gon float8
Note: <@Value(DatasetName)>: [SDF3]
fastighet_y00 (writer SDF3_1)
    attributes: td_ho_verksamhet_1 char(200), ho_hardgjordyta char(200), ho_classification char(200), ho_propertyvalue char(200), radianer char(200), grader char(200), gon char(200)
Note: <@Value(DatasetName)>: PG_DATALAGER_ADMSRV0118 [POSTGIS] - 2
Table1 (writer POSTGIS_7)
    attributes: td_ho_verksamhet_1 varchar(200), ho_hardgjordyta varchar(200), ho_classification varchar(200), ho_propertyvalue varchar(200), radianer float8, grader float8, gon float8
AttributeKeeper_3
    CREATE_BULK_MODE_FEATURES = No
    KEEP_ATTRS = gon,radianer,td_ma_verksamhet_1,grader,DatasetName,ma_markanvandningtyp,td_notering_text_1,td_ma_verksamhet_2
    -> AttributeManager_3
    -> fastighet_y0000 (writer SDF3_1)
    -> Junction_12
    -> Table1 (writer POSTGIS_3)
    -> Table1 (writer POSTGIS_8)
AttributeManager_3
    ATTR_TABLE:
      RENAME_SET_VALUE td_notering_text_1 > not_txt_1
      RENAME_SET_VALUE ma_markanvandningtyp > ma_typ
      RENAME_SET_VALUE td_ma_verksamhet_1 > td_ma_v_1
      RENAME_SET_VALUE td_ma_verksamhet_2 > td_ma_v_2
    -> Shapefile10000 (writer SHAPEFILE_1)
Note: <@Value(DatasetName)>: [SHAPEFILE]
Shapefile10000 (writer SHAPEFILE_1)
    attributes: not_txt_1 char(200), ma_typ char(200), td_ma_v_1 char(200), td_ma_v_2 char(200), radianer double, grader double, gon double
Note: <@Value(DatasetName)>: [SDF3]
fastighet_y0000 (writer SDF3_1)
    attributes: td_notering_text_1 char(200), ma_markanvandningtyp char(200), td_ma_verksamhet_1 char(200), td_ma_verksamhet_2 char(200), radianer char(200), grader char(200), gon char(200)
Note: <@Value(DatasetName)>: PG_DATALAGER [POSTGIS] - 3
Table1 (writer POSTGIS_3)
    attributes: td_notering_text_1 varchar(200), ma_markanvandningtyp varchar(200), td_ma_verksamhet_1 varchar(200), td_ma_verksamhet_2 varchar(200), radianer float8, grader float8, gon float8
Note: <@Value(DatasetName)>: PG_DATALAGER_ADMSRV0118 [POSTGIS] - 3
Table1 (writer POSTGIS_8)
    attributes: ma_markanvandningtyp varchar(200), td_ma_verksamhet_1 varchar(200), td_ma_verksamhet_2 varchar(200), td_notering_text_1 varchar(200), radianer float8, grader float8, gon float8
AttributeKeeper_6
    CREATE_BULK_MODE_FEATURES = NO
    KEEP_ATTRS = gon,radianer,grader,DatasetName,td_notering_text_1,md_markdetaljtyp,md_marklinje,md_planlagetyp,td_md_verksamhet_1,td_md_verksamhet_2
    -> Junction_12
    -> AttributeManager_6
    -> fastighet_y000100 (writer SDF3_1)
    -> Table1 (writer POSTGIS_11)
    -> Table1 (writer POSTGIS_12)
AttributeManager_6
    ATTR_TABLE:
      RENAME_SET_VALUE md_markdetaljtyp > md_dettyp
      RENAME_SET_VALUE td_md_verksamhet_1 > td_md_v_1
      RENAME_SET_VALUE td_md_verksamhet_2 > td_md_v_2
      RENAME_SET_VALUE md_marklinje > md_marklin
      RENAME_SET_VALUE md_planlagetyp > md_plagtyp
      RENAME_SET_VALUE td_notering_text_1 > not_txt_1
    -> Shapefile100000000 (writer SHAPEFILE_1)
Note: <@Value(DatasetName)>: [SHAPEFILE]
Shapefile100000000 (writer SHAPEFILE_1)
    attributes: md_dettyp char(200), td_md_v_1 char(200), td_md_v_2 char(200), md_marklin char(200), md_plagtyp char(200), not_txt_1 char(200), radianer double, grader double, gon double
Note: <@Value(DatasetName)>: [SDF3]
fastighet_y000100 (writer SDF3_1)
    attributes: md_markdetaljtyp char(200), td_md_verksamhet_1 char(200), td_md_verksamhet_2 char(200), md_marklinje char(200), md_planlagetyp char(200), td_notering_text_1 char(200), radianer double, grader double, gon double
Table1 (writer POSTGIS_11)
    attributes: md_markdetaljtyp varchar(200), td_md_verksamhet_1 varchar(200), td_md_verksamhet_2 varchar(200), md_marklinje varchar(200), md_planlagetyp varchar(200), td_notering_text_1 varchar(200), radianer float8, grader float8, gon float8
Table1 (writer POSTGIS_12)
    attributes: md_markdetaljtyp varchar(200), td_md_verksamhet_1 varchar(200), td_md_verksamhet_2 varchar(200), md_marklinje varchar(200), md_planlagetyp varchar(200), td_notering_text_1 varchar(200), radianer float8, grader float8, gon float8
AttributeKeeper_4
    CREATE_BULK_MODE_FEATURES = No
    KEEP_ATTRS = td_ml_verksamhet_1,ml_markdetaljtyp,gon,radianer,grader,td_ml_verksamhet_2,DatasetName,ml_planlagetyp,ml_marklinje,td_notering_text_1
    -> AttributeManager_4
    -> fastighet_y0001 (writer SDF3_1)
    -> Junction_12
    -> Table1 (writer POSTGIS_4)
    -> Table1 (writer POSTGIS_9)
AttributeManager_4
    ATTR_TABLE:
      RENAME_SET_VALUE ml_markdetaljtyp > ml_dettyp
      RENAME_SET_VALUE td_ml_verksamhet_1 > td_ml_v_1
      RENAME_SET_VALUE td_ml_verksamhet_2 > td_ml_v_2
      RENAME_SET_VALUE ml_marklinje > ml_marklin
      RENAME_SET_VALUE ml_planlagetyp > ml_plagtyp
      RENAME_SET_VALUE td_notering_text_1 > not_txt_1
    -> Shapefile1000000 (writer SHAPEFILE_1)
Note: <@Value(DatasetName)>: [SHAPEFILE]
Shapefile1000000 (writer SHAPEFILE_1)
    attributes: ml_dettyp char(200), td_ml_v_1 char(200), td_ml_v_2 char(200), ml_marklin char(200), ml_plagtyp char(200), not_txt_1 char(200), radianer double, grader double, gon double
Note: <@Value(DatasetName)>: [SDF3]
fastighet_y0001 (writer SDF3_1)
    attributes: ml_markdetaljtyp char(200), td_ml_verksamhet_1 char(200), td_ml_verksamhet_2 char(200), ml_marklinje char(200), ml_planlagetyp char(200), td_notering_text_1 char(200), radianer char(200), grader char(200), gon char(200)
Note: <@Value(DatasetName)>: PG_DATALAGER [POSTGIS] - 4
Table1 (writer POSTGIS_4)
    attributes: ml_markdetaljtyp varchar(200), td_ml_verksamhet_1 varchar(200), td_ml_verksamhet_2 varchar(200), ml_marklinje varchar(200), ml_planlagetyp varchar(200), td_notering_text_1 varchar(200), radianer float8, grader float8, gon float8
Note: <@Value(DatasetName)>: PG_DATALAGER_ADMSRV0118 [POSTGIS] - 4
Table1 (writer POSTGIS_9)
    attributes: td_notering_text_1 varchar(200), ml_markdetaljtyp varchar(200), td_ml_verksamhet_1 varchar(200), td_ml_verksamhet_2 varchar(200), ml_marklinje varchar(200), ml_planlagetyp varchar(200), radianer float8, grader float8, gon float8, datasetname text
AttributeKeeper_5
    CREATE_BULK_MODE_FEATURES = No
    KEEP_ATTRS = td_namntyp,td_verksamhet_2,gon,radianer,grader,DatasetName,td_verksamhet_1,td_namn_1
    -> AttributeManager_5
    -> fastighet_y0002 (writer SDF3_1)
    -> Junction_12
    -> Table1 (writer POSTGIS_5)
    -> Table1 (writer POSTGIS_10)
AttributeManager_5
    ATTR_TABLE:
      RENAME_SET_VALUE td_verksamhet_1 > td_v_1
      RENAME_SET_VALUE td_verksamhet_2 > td_v_2
    -> Shapefile1000001 (writer SHAPEFILE_1)
Note: <@Value(DatasetName)>: [SHAPEFILE]
Shapefile1000001 (writer SHAPEFILE_1)
    attributes: td_namntyp char(200), td_v_1 char(200), td_v_2 char(200), td_namn_1 char(200), radianer double, grader double, gon double
Junction_12
    -> Aggregator
Note: <@Value(DatasetName)>: [SDF3]
fastighet_y0002 (writer SDF3_1)
    attributes: td_namntyp char(200), td_verksamhet_1 char(200), td_verksamhet_2 char(200), td_namn_1 char(200), radianer char(200), grader char(200), gon char(200)
Note: <@Value(DatasetName)>: PG_DATALAGER [POSTGIS] - 5
Table1 (writer POSTGIS_5)
    attributes: td_namntyp varchar(200), td_verksamhet_1 varchar(200), td_verksamhet_2 varchar(200), td_namn_1 varchar(200), radianer float8, grader float8, gon float8
Note: <@Value(DatasetName)>: PG_DATALAGER_ADMSRV0118 [POSTGIS] - 5
Table1 (writer POSTGIS_10)
    attributes: td_namntyp varchar(200), td_verksamhet_1 varchar(200), td_verksamhet_2 varchar(200), td_namn_1 varchar(200), radianer float8, grader float8, gon float8
Junction_11
    -> Aggregator_6
Junction_5
    -> Aggregator_5

Bookmark: Loggning
Note: AttributeCreator_12_-_FeatureMerger_3
Junction_2
    -> FeatureMerger_2 [SUPPLIER]
Note: AttributeCreator_12_-_FeatureMerger_3
Junction_4
    -> FeatureMerger_3 [SUPPLIER]
Junction_8
    -> FeatureMerger_5 [SUPPLIER]
Junction_10
    -> FeatureMerger_6 [SUPPLIER]
Note: Junction_11 : Output
Junction_15
    -> Junction_6
Junction_6
    -> FeatureMerger_4 [SUPPLIER]
Aggregator
    ACCUM_ATTRS_NAME = Use Attributes From One Feature
    AGGREGATE_TYPE = Homogeneous Collection (If Possible)
    COUNT_ATTR = Antal
    MODE = Geometry - Assemble One Level
    ORDERED = No
    SEP = ,
    AGGREGATE -> AttributeCreator_7
AttributeCreator_7
    ATTR_TABLE = SET_TO _FeatureIdMerger = 1
    -> FeatureMerger_6 [REQUESTOR]
FeatureMerger_6
    ATTR_ACCUM_MODE = Merge Supplier
    ATTR_CONFLICT_RES = Use Requestor
    CLEANING_TOLERANCE = None
    IGNORE_NULLS = No
    JOIN_KEYS = @Value(_FeatureIdMerger) @Value(_FeatureIdMerger) AUTO
    MERGE_TYPE = Attributes Only
    PROCESS_DUPS = No
    REJECT_NULL_MISSING_KEYS = No
    SUPPLIERS_FIRST = No
    MERGED -> StringConcatenator_5
StringConcatenator_5
    ACTION = Create New Attribute
    PARM_LINE = Process @Value(ProcessName) har färdigbehandlat @Value(Antal) st. objekt.
    VAL_ATTR = Logg
    -> DTStamperYYYY-MM-DD_HH:MI:SS.sss_5
DTStamperYYYY-MM-DD_HH:MI:SS.sss_5
    -> Logg_5
Logg_5: WorkspaceRunner
    BLOCKING = No
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,KLART,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Aggregator_6
    ACCUM_ATTRS_NAME = Use Attributes From One Feature
    AGGREGATE_TYPE = Homogeneous Collection (If Possible)
    COUNT_ATTR = Antal
    GROUP_BY = fme_rejection_code
    MODE = Geometry - Assemble One Level
    ORDERED = No
    SEP = ", "
    AGGREGATE -> AttributeCreator_15
AttributeCreator_15
    ATTR_TABLE = SET_TO _FeatureIdMerger = 1
    -> FeatureMerger_4 [REQUESTOR]
FeatureMerger_4
    ATTR_ACCUM_MODE = Merge Supplier
    ATTR_CONFLICT_RES = Use Requestor
    CLEANING_TOLERANCE = None
    IGNORE_NULLS = No
    JOIN_KEYS = @Value(_FeatureIdMerger) @Value(_FeatureIdMerger) AUTO
    MERGE_TYPE = Attributes Only
    PROCESS_DUPS = No
    REJECT_NULL_MISSING_KEYS = No
    SUPPLIERS_FIRST = No
    MERGED -> StringConcatenator_3
StringConcatenator_3
    ACTION = Create New Attribute
    PARM_LINE = fme_basicstring:48%26:FeatureMerge av objekt och text ej möjlig. Fel: @Value(fme_rejection_code)
    VAL_ATTR = Logg
    -> DTStamperYYYY-MM-DD_HH:MI:SS.sss_3
DTStamperYYYY-MM-DD_HH:MI:SS.sss_3
    -> Logg_4
Logg_4: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Aggregator_5
    ACCUM_ATTRS_NAME = Use Attributes From One Feature
    AGGREGATE_TYPE = Homogeneous Collection (If Possible)
    COUNT_ATTR = Antal
    GROUP_BY = _reader_error
    MODE = Geometry - Assemble One Level
    ORDERED = No
    SEP = ", "
    AGGREGATE -> AttributeCreator_6
AttributeCreator_6
    ATTR_TABLE = SET_TO _FeatureIdMerger = 1
    -> FeatureMerger_5 [REQUESTOR]
FeatureMerger_5
    ATTR_ACCUM_MODE = Merge Supplier
    ATTR_CONFLICT_RES = Use Requestor
    CLEANING_TOLERANCE = None
    IGNORE_NULLS = No
    JOIN_KEYS = @Value(_FeatureIdMerger) @Value(_FeatureIdMerger) AUTO
    MERGE_TYPE = Attributes Only
    PROCESS_DUPS = No
    REJECT_NULL_MISSING_KEYS = No
    SUPPLIERS_FIRST = No
    MERGED -> StringConcatenator_7
StringConcatenator_7
    ACTION = Create New Attribute
    PARM_LINE = Texter kunde inte hämtas. Fel: @Value(_reader_error)
    VAL_ATTR = Logg
    -> DTStamperYYYY-MM-DD_HH:MI:SS.sss_4
DTStamperYYYY-MM-DD_HH:MI:SS.sss_4
    -> Logg_6
Logg_6: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: Följande kolumn förekommer fler än / en gång för specifikt dataset
Aggregator_4
    ACCUM_ATTRS_NAME = Use Attributes From One Feature
    AGGREGATE_TYPE = Homogeneous Collection (If Possible)
    COUNT_ATTR = Antal
    GROUP_BY = dl_new_column_name
    MODE = Geometry - Assemble One Level
    ORDERED = No
    SEP = ", "
    AGGREGATE -> AttributeCreator_4
AttributeCreator_4
    ATTR_TABLE = SET_TO _FeatureIdMerger = 1
    -> FeatureMerger_3 [REQUESTOR]
FeatureMerger_3
    ATTR_ACCUM_MODE = Merge Supplier
    ATTR_CONFLICT_RES = Use Requestor
    CLEANING_TOLERANCE = None
    IGNORE_NULLS = No
    JOIN_KEYS = @Value(_FeatureIdMerger) @Value(_FeatureIdMerger) AUTO
    MERGE_TYPE = Attributes Only
    PROCESS_DUPS = No
    REJECT_NULL_MISSING_KEYS = No
    SUPPLIERS_FIRST = No
    MERGED -> StringConcatenator_6
StringConcatenator_6
    ACTION = Create New Attribute
    PARM_LINE = Följande @Value(Antal)  st. kolumner finns det dubbletter för (@Value(dl_new_column_name)). För att exporterad data vara läsbar enligt manifest, ändra kolumnnamn i manifest.
    VAL_ATTR = Logg
    -> DTStamperYYYY-MM-DD_HH:MI:SS.sss_2
DTStamperYYYY-MM-DD_HH:MI:SS.sss_2
    -> Logg_3
Logg_3: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: Endast som signal att starta logg
Sampler_2
    RATE = 1
    SAMPLE_MODE = No
    SAMPLE_TYPE_LONG = First N Features
    SAMPLED -> AttributeCreator_13
AttributeCreator_13
    ATTR_TABLE = SET_TO _FeatureIdMerger = 1
    -> FeatureMerger_2 [REQUESTOR]
FeatureMerger_2
    ATTR_ACCUM_MODE = Merge Supplier
    ATTR_CONFLICT_RES = Use Requestor
    CLEANING_TOLERANCE = None
    IGNORE_NULLS = No
    JOIN_KEYS = @Value(_FeatureIdMerger) @Value(_FeatureIdMerger) AUTO
    MERGE_TYPE = Attributes Only
    PROCESS_DUPS = No
    REJECT_NULL_MISSING_KEYS = No
    SUPPLIERS_FIRST = No
    MERGED -> StringConcatenator_2
StringConcatenator_2
    ACTION = Create New Attribute
    PARM_LINE = Kör @Value(ProcessName) för data definierad i "$(SchemaFlush)" till datalagret.
    VAL_ATTR = Logg
    -> DTStamperYYYY-MM-DD_HH:MI:SS.sss
DTStamperYYYY-MM-DD_HH:MI:SS.sss
    -> Logg_2
Logg_2: WorkspaceRunner
    BLOCKING = No
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,INFORMATION,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)

Bookmark: Kontrollera om kolumnnamn förekommer fler än en gång per dataset
Tester_2
    BOOL_OP = AND
    TEST_CLAUSE:
      TEST @Value(dl_need_new_column_name) = true
      TEST @Value(dl_new_column_name) ATTRIBUTE_HAS_VALUE ""
    TEST_MODE = TEST
    PASSED -> AttributeCreator
AttributeCreator
    ATTR_TABLE = SET_TO column_name = @Value(dl_new_column_name)
    -> Aggregator_2
Aggregator_2
    ACCUM_ATTRS_NAME = Use Attributes From One Feature
    AGGREGATE_TYPE = Homogeneous Collection (If Possible)
    COUNT_ATTR = AntalSameColumns
    GROUP_BY = fme_feature_type_name dl_new_column_name
    MODE = Geometry - Assemble One Level
    ORDERED = No
    SEP = ,
    AGGREGATE -> Tester_3
Tester_3
    BOOL_OP = OR
    TEST_CLAUSE = TEST @Value(AntalSameColumns) > 1
    TEST_MODE = TEST
    PASSED -> Aggregator_4

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    INCLUDE_OFFSET = NO
    STAMP_TYPE = datetime
    TIMEZONE = local
    -> DateTimeConverter
DateTimeConverter
    DATETIME_ATTR = _dts
    OUT_FORMAT = %Y-%m-%d %H:%M:%S
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    NO_MATCH = _FME_NO_OP_
    REGEXP = YES
    SRC_ATTRS = _dts
    -> StringReplacer_2
StringReplacer_2
    CASE = NO
    FIND_TEXT = .*\.
    NO_MATCH = _FME_NO_OP_
    REGEXP = YES
    SRC_ATTRS = _mils
    -> SubstringExtractor
SubstringExtractor
    END = 2
    RESULT_ATTR = _subMils
    SRC_STRING = @Value(_mils)
    START = 0
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)

FME custom transformer vektor2vinklar

Input (input)
    -> CoordinateExtractor
ExpressionEvaluator_22
    ACTION = Create New Attribute
    EXPRESSION = @Value(radianer)*180/@pi()
    VAL_ATTR = grader
    -> TestFilter_5
Note: Sätter ingen vridning
AttributeCreator_6
    ATTR_TABLE:
      SET_TO radianer = 0
      SET_TO grader = 0
      SET_TO gon = 100
    -> Junction_4
VertexCreator_7
    MODE_NAME = Replace with Point
    XVAL = @Value(x1)
    YVAL = @Value(y1)
    -> AttributeRemover
AttributeRemover
    LIST_ATTRS = _indices{}
    REMOVE_ATTRS = y2,y1,diffY,z2,radianer2gon,diffX,x1,radianer2grader,x2,z1
    -> Output (output)
Output (output)

Bookmark: Koordinatdiffar i x- och y-led
CoordinateExtractor
    LIST_NAME = _indices
    MODE = All Coordinates
    -> AttributeCreator
AttributeCreator
    ATTR_TABLE:
      SET_TO x1 = @Value(_indices{0}.x)
      SET_TO y1 = @Value(_indices{0}.y)
      SET_TO z1 = @Value(_indices{0}.z)
      SET_TO x2 = @Value(_indices{1}.x)
      SET_TO y2 = @Value(_indices{1}.y)
      SET_TO z2 = @Value(_indices{1}.z)
    -> AttributeCreator_5
AttributeCreator_5
    ATTR_TABLE:
      SET_TO diffX = @Evaluate(@Value(x2)-@Value(x1))
      SET_TO diffY = @Evaluate(@Value(y2)-@Value(y1))
    -> ExpressionEvaluator_16

Bookmark: Radianer höger- och vänstervridet
ExpressionEvaluator_16
    ACTION = Create New Attribute
    EXPRESSION = @atan2(@Value(diffY),@Value(diffX))
    VAL_ATTR = radianer2grader
    -> ExpressionEvaluator_17
ExpressionEvaluator_17
    ACTION = Create New Attribute
    EXPRESSION = @atan2(@Value(diffX),@Value(diffY))
    VAL_ATTR = radianer2gon
    -> TestFilter_4

Bookmark: Teckenhantering radianer/grader
TestFilter_4
    DEFAULT_VALUE = <UNFILTERED>
    TEST_LIST:
      "BOOL_OP,AND,COMPOSITE_TEST,""""""<Unused>"""""",TEST_CLAUSE,TEST @Value(diffX) > 0
      TEST @Value(diffY) > 0",Kvadrant 1,"BOOL_OP,AND,COMPOSITE_TEST,""""""<Unused>"""""",TEST_CLAUSE,TEST @Value(diffX) < 0
      TEST @Value(diffY) > 0",Kvadrant 2,"BOOL_OP,AND,COMPOSITE_TEST,""""""<Unused>"""""",TEST_CLAUSE,TEST @Value(diffX) < 0
      TEST @Value(diffY) < 0",Kvadrant 3,"BOOL_OP,AND,COMPOSITE_TEST,""""""<Unused>"""""",TEST_CLAUSE,TEST @Value(diffX) > 0
      TEST @Value(diffY) < 0",Kvadrant 4
    Kvadrant 1 -> AttributeCopier_3
    Kvadrant 2 -> AttributeCopier_3
    Kvadrant 3 -> ExpressionEvaluator_18
    Kvadrant 4 -> ExpressionEvaluator_18
    <UNFILTERED> -> AttributeCreator_6
AttributeCopier_3
    ATTR_TABLE = COPY radianer2grader > radianer
    -> Junction_3
ExpressionEvaluator_18
    ACTION = Create New Attribute
    EXPRESSION = @Value(radianer2grader)+2*@pi()
    VAL_ATTR = radianer
    -> Junction_3
Junction_3
    -> ExpressionEvaluator_22

Bookmark: Teckenhantering gon (nygrader)
TestFilter_5
    DEFAULT_VALUE = <UNFILTERED>
    TEST_LIST:
      "BOOL_OP,AND,COMPOSITE_TEST,""""""<Unused>"""""",TEST_CLAUSE,TEST @Value(diffY) > 0
      TEST @Value(diffX) > 0",Kvadrant 1,"BOOL_OP,AND,COMPOSITE_TEST,""""""<Unused>"""""",TEST_CLAUSE,TEST @Value(diffY) < 0
      TEST @Value(diffX) > 0",Kvadrant 2,"BOOL_OP,AND,COMPOSITE_TEST,""""""<Unused>"""""",TEST_CLAUSE,TEST @Value(diffY) < 0
      TEST @Value(diffX) < 0",Kvadrant 3,"BOOL_OP,AND,COMPOSITE_TEST,""""""<Unused>"""""",TEST_CLAUSE,TEST @Value(diffY) > 0
      TEST @Value(diffX) < 0",Kvadrant 4
    Kvadrant 1 -> ExpressionEvaluator_19
    Kvadrant 2 -> ExpressionEvaluator_19
    Kvadrant 3 -> ExpressionEvaluator_20
    Kvadrant 4 -> ExpressionEvaluator_21
ExpressionEvaluator_19
    ACTION = Create New Attribute
    EXPRESSION = @Value(radianer2gon)*200/@pi()
    VAL_ATTR = gon
    -> Junction_4
ExpressionEvaluator_20
    ACTION = Create New Attribute
    EXPRESSION = @Value(radianer2gon)*200/@pi()+400
    VAL_ATTR = gon
    -> Junction_4
ExpressionEvaluator_21
    ACTION = Create New Attribute
    EXPRESSION = @Value(radianer2gon)*200/@pi()+400
    VAL_ATTR = gon
    -> Junction_4
Junction_4
    -> VertexCreator_7
