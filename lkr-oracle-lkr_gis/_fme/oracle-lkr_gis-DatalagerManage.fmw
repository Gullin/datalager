FME workspace oracle-lkr_gis-DatalagerManage.fmw

Parameters:
- RotDirectory = ../   # Katalogen där processen startar
- ProcessName =   # Processnamn
- InData = LKR_GIS.GIS_V_BLADINDELNING
- OutputDirectory = C:\LKR_GIS\Datalager_procsrc\_geodatarepo\landskrona\lkr_gis   # Katalog för lagring av del av datalager
- SourceDataset_TEXTLINE = C:\LKR_GIS\Datalager_procsrc\lkr-oracle-lkr_gis\_schema\database-objects-to-read.txt   # Source Text File(s)
- DatabaseSchema = LKR_GIS   # Databasschema
- DestDataset_ESRISHAPE = C:\LKR_GIS\Datalager_procsrc\_geodatarepo\landskrona\lkr_gis   # Destination Esri Shapefile Folder
- SourceDataset_ORACLE_SPATIAL = LKR_GIS   # Connection

Readers:
- ORACLE_SPATIAL_1: ORACLE_SPATIAL from $(SourceDataset_ORACLE_SPATIAL)
- TEXTLINE_1: TEXTLINE from $(SourceDataset_TEXTLINE)

Writers:
- SDF3_1: SDF3 to $(OutputDirectory)
- ESRISHAPE_1: ESRISHAPE to $(OutputDirectory)
- ESRISHAPE_2: ESRISHAPE to $(DestDataset_ESRISHAPE)

text_line (reader TEXTLINE_1)
    attributes: text_line_data buffer
    -> FeatureReader [INITIATOR]
FeatureReader
    INTERACT = <No Spatial Filter>
    ORACLE_SPATIAL_QUERY_FEATURE_TYPES_FOR_MERGE_FILTERS = Yes
    ORACLE_SPATIAL_SHOW_SYSTEM_TABLES = NO
    OUTPUT_FEATURES_DISPLAY = Schema and Data Features
    ORACLE_SPATIAL_USE_UNIFIED_DATE_ATTRS = YES
    ATTR_ACCUM_MODE = Only Use Result
    ORACLE_SPATIAL_NAMED_CONNECTION = $(DatabaseSchema)
    ORACLE_SPATIAL_USE_SEARCH_ENVELOPE = NO
    FEATURETYPES = @Value(text_line_data)
    ORACLE_SPATIAL_CLIP_TO_ENVELOPE = NO
    ORACLE_SPATIAL_PARSE_MAPINFO_SYMBOLOGY = NO
    ORACLE_SPATIAL_REMOVE_SCHEMA_QUALIFIER = NO
    COMBINE_GEOM = Use Result
    ORACLE_SPATIAL_CHUNK_SIZE = 200
    DATASET = $(DatabaseSchema)
    FORMAT = ORACLE_SPATIAL
    ORACLE_SPATIAL_SERVER_TYPE = ORACLE8i
    ORACLE_SPATIAL_HANDLE_MULTIPLE_SPATIAL_COLUMNS = NO
    ORACLE_SPATIAL_PERSISTENT_CONNECTION = YES
    ORACLE_SPATIAL_READ_3D_POLYGON_AS_FACE = NO
    <OTHER> -> Shapefile1 (writer ESRISHAPE_2)
Shapefile1 (writer ESRISHAPE_2)
LKR_GIS.GIS_V_VALDISTRIKT (reader ORACLE_SPATIAL_1) [off]
    attributes: KEY number(10,0), VALDISTRIKTNAMN_2006 varchar2(100), VALDISTRIKTNAMN_2006_ID number(10,0), VALDISTRIKTNAMN varchar2(100), VALLOKAL varchar2(100), VALLOKAL_BELADRESS varchar2(100), VALLOKAL_POSTNUMMER varchar2(5), VALLOKAL_POSTADRESS varchar2(100), TAX_PERSORGNR varchar2(13), FORVTYP_L varchar2(1), BYGGNAD_TYP number(10,0), USE varchar2(32), TOMTR_PERSORGNR varchar2(13), ADRESSTATUS varchar2(35), AKT_PB varchar2(3), TEXTVALUE_TBD varchar2(128), DAT_GENOMF_F varchar2(10), SKALANPASSNING char(1), VERTICALACCURACY_VALUE number(10,3), KM_01_BESK varchar2(255), PLANNAMN varchar2(300), PLANFK varchar2(6), AREA number(20,8), ADRESSPLATS varchar2(9), POSTORT varchar2(27), KM_03_BESK varchar2(255), DAT_GENOMF_T varchar2(10), APM_02_BESK_KORT varchar2(30), ADRESSOMR varchar2(71), FID_GEOM number(10,0),
      KK_SKYDDKAT_BM number(1,0), APM_02_BESK varchar2(255), KAR_OBJ number(10,0), HORIZONTALCOORDINATESYSTEM varchar2(30), BLADTYP varchar2(5), KM_05_BESK varchar2(255), POSITIONKIND varchar2(32), DAT_SENASTAJOUR varchar2(10), APM_02 number(2,0), KAR_EGN number(10,0), BEV_PLATS_FASTIGHET varchar2(50), BEV_PABORJAT date, OBJVALUE varchar2(255), ADRESSOMRADES_ID varchar2(36), OBJECTSTATUS varchar2(35), HORIZONTALACCURACY_VALUE number(8,3), KM_03_BESK_KORT varchar2(30), KK_BESKRIVNING varchar2(255), APM_01_BESK varchar2(255), TOMTR_AGARENAMN varchar2(300), EXTENSIONYEAR varchar2(4), UUID varchar2(36), APM_03 number(2,0), DAT_LAGAKRAFT varchar2(10), Z_TAKFOT number(20,8), BYGGNAD_OBJ number(10,0), CONSTRUCTIONYEAR varchar2(4), BEV_PLATS_ADRESSOMRADE varchar2(71), KK_ARKITEKT varchar2(255), KK_SKYDDKAT_RL number(1,0),
      PDF varchar2(255), BEV_PLATS_OVRIGT varchar2(255), KM_05_BESK_KORT varchar2(30), KK_SKYDDKAT_DPS number(1,0), TOMTR varchar2(1), KK_SKYDDKAT_BPA number(1,0), BEV_UTFORARE varchar2(32), FID_BYGGNAD number(10,0), ATTEFALL_KOMP number(1,0), APM_01_BESK_KORT varchar2(30), EGN_BESK varchar2(255), KM_02_BESK varchar2(255), KM_02 number(2,0), ADRESSTYP varchar2(35), KK_SKYDDKAT_OB number(1,0), BELONGSTO number(12,0), OBJECTVERSION number(10,0), BLADNAMN varchar2(50), OBJ_BESK varchar2(255), KAR_TYP number(10,0), FASTIGHET_ID number(12,0), PLAN_ID number(12,0), PLANAVGIFT varchar2(3), BEV_NOTERING varchar2(255), KM_03 number(2,0), KK_SKYDSSKAT_PRIO varchar2(3), KM_02_BESK_KORT varchar2(30), USER_MODIFIED varchar2(32), ATTEFALL_INREDD number(1,0), POSTNUMMER number(5,0),
      ATTEFALL_KOMPBOST number(1,0), STATUS_TEXT varchar2(13), KM_04_BESK_KORT varchar2(30), BELADRESS varchar2(83), LIESON_FASTIGHET varchar2(50), BEV_AVSLUTAT date, BLADKVADRANT varchar2(2), HOUSENUMBER number(10,0), DAT_GALLER_T varchar2(10), KM_05 number(2,0), KK_SKYDDSFORMULERING varchar2(400), FASTIGHET varchar2(64), BEV_PLATS_ADRESS varchar2(83), HREF_PDF varchar2(255), KM_04_BESK varchar2(255), KK_SKYDDKAT_BPO number(1,0), KK_BENAMNING_POPNAMN varchar2(255), OMRADE number, ATTEFALL_TAKKUPA number(1,0), KK_SKYDDS_AR number(4,0), SCHEMA_NAME char(7), LIESON number(12,0), APM_01 number(2,0), APM_03_BESK varchar2(255), BEV_BESKRIVNING varchar2(255), FORVTYP_T varchar2(1), LAG_PERSORGNR varchar2(13), USE_VALUE number, STATUS char(1), KK_SKYDDKAT_VBM number(1,0),
      ATTEFALL_TILLBYGGNAD number(1,0), ADRESSPLATS_ID varchar2(36), FEATURECLASS varchar2(8), EGN_KOD number(10,0), TYP_BESK varchar2(255), AKT_EGN varchar2(18), TABLE_NAME char(13), FEATURETYPE varchar2(7), USETYPE varchar2(32), DATE_MODIFIED date, KM_01 number(2,0), KM_01_BESK_KORT varchar2(30), BEV_INKOMMET date, KM_04 number(2,0), BELONGSTO_FASTIGHET varchar2(50), KK_SKYDD_K number(1,0), DAT_BESLUT varchar2(10), LITTERA varchar2(2), APM_03_BESK_KORT varchar2(30), FORVTYP char(1), KK_SKYDD_Q_LILLA number(1,0), KK_SKYDD_Q_STORA number(1,0), OBJECTSTATUS_VALUE number, LAG_AGARENAMN varchar2(300), TYPVALUE varchar2(255), KK_BYGGNAD_ID varchar2(36), AKT varchar2(18), KK_SKYDDKAT_AL number(1,0)
    -> ParameterFetcher
ParameterFetcher
    ATTR_LIST = ProcessName $(ProcessName) RotDirectory $(RotDirectory) InData $(InData)
    -> UUIDGenerator
UUIDGenerator
    UUID_ATTR = ProcessID
    -> Sampler_2
    -> GeometryFilter
    -> AttributeCreator
AttributeCreator
    ATTR_TABLE = SET_TO DatasetName = @Value(fme_feature_type)
    -> StringCaseChanger_2
StringCaseChanger_2
    ATTRLIST = DatasetName
    CHANGE_TYPE = lowercase
    ATTRCHOICE = Selected Attributes
    -> FeatureClass1 (writer SDF3_1)
Note: : lkr_gis [SDF3]
FeatureClass1 (writer SDF3_1)
GeometryFilter
    GEOM_PORT_NAMES = Point Line Arc Area Ellipse Text Raster "Point Cloud" Surface Solid Collection Null Instance
    BREAK_AGG = No
    POINT -> StringConcatenator
    LINE -> StringConcatenator_4
    ARC -> StringConcatenator_4
    AREA -> StringConcatenator_5
    ELLIPSE -> StringConcatenator_5
    TEXT -> StringConcatenator_6
    RASTER -> Aggregator
    POINTCLOUD -> Aggregator
    SURFACE -> Aggregator
    SOLID -> Aggregator
    COLLECTION -> Aggregator
    NULL -> Aggregator
    INSTANCE -> Aggregator
    <UNFILTERED> -> Aggregator
StringConcatenator
    VAL_ATTR = DatasetName
    ACTION = Create New Attribute
    PARM_LINE = @Value(fme_feature_type)_p
    -> Junction
StringConcatenator_4
    VAL_ATTR = DatasetName
    ACTION = Create New Attribute
    PARM_LINE = @Value(fme_feature_type)_l
    -> Junction
StringConcatenator_5
    VAL_ATTR = DatasetName
    ACTION = Create New Attribute
    PARM_LINE = @Value(fme_feature_type)_y
    -> Junction
    -> StringCaseChanger
StringCaseChanger
    ATTRLIST = DatasetName
    CHANGE_TYPE = lowercase
    ATTRCHOICE = Selected Attributes
    -> Shapefile100 (writer ESRISHAPE_1)
Note: : lkr_gis [ESRISHAPE]
Shapefile100 (writer ESRISHAPE_1)
StringConcatenator_6
    VAL_ATTR = DatasetName
    ACTION = Create New Attribute
    PARM_LINE = @Value(fme_feature_type)_t
    -> Junction
Junction [off]
    -> Shapefile1 (writer ESRISHAPE_1)
Note: : lkr_gis [ESRISHAPE]
Shapefile1 (writer ESRISHAPE_1) [off]

Bookmark: Loggning
Aggregator
    ACCUM_ATTRS_NAME = Use Attributes From One Feature
    AGGREGATE_TYPE = Homogeneous Collection (If Possible)
    MODE = Geometry - Assemble One Level
    SEP = ,
    ORDERED = No
    GROUP_BY = fme_feature_type
    AGGREGATE -> Aggregator_3
Aggregator_3
    ACCUM_ATTRS_NAME = Use Attributes From One Feature
    CONCAT_ATTRS = fme_feature_type
    AGGREGATE_TYPE = Homogeneous Collection (If Possible)
    MODE = Geometry - Assemble One Level
    COUNT_ATTR = Antal
    SEP = ", "
    ORDERED = No
    AGGREGATE -> StringConcatenator_3
StringConcatenator_3
    VAL_ATTR = Logg
    ACTION = Create New Attribute
    PARM_LINE = Geometrier från objektklasser (@Value(fme_feature_type)) skrivs ej till shape-filer.
    -> TimeStamper_3
TimeStamper_3
    TIME_ATTR = Timestamp
    FMT = ^Y-^m-^d ^H:^M:^S
    -> Logg_3
Logg_3: WorkspaceRunner
    WORKSPACE_PARAMETERS = EX_DATE_TIME,@Value(Timestamp),EX_PROCESS_NAME,@Value(ProcessName),EX_ID,@Value(ProcessID),EX_TYPE,VARNING,EX,@Value(Logg),EX_WorkSpace,$(FME_MF_DIR_USERTYPED)$(FME_MF_NAME),EX_ROT_DIRECTORY,@Value(RotDirectory)
    BLOCKING = No
    WORKSPACE_FILE = C:\dev\Datalager_procsrc\_sys\_logg.fmw
Note: Endast till för som signal att starta logg
Sampler_2
    SAMPLE_MODE = No
    SAMPLE_TYPE_LONG = First N Features
    RATE = 1
    SAMPLED -> StringConcatenator_2
StringConcatenator_2
    VAL_ATTR = Logg
    ACTION = Create New Attribute
    PARM_LINE = Kör @Value(ProcessName) för data "@Value(InData)" till datalagret.
    -> TimeStamper_2
TimeStamper_2
    TIME_ATTR = Timestamp
    FMT = ^Y-^m-^d ^H:^M:^S
    -> Logg_2
Logg_2: WorkspaceRunner
    WORKSPACE_PARAMETERS = EX_DATE_TIME,@Value(Timestamp),EX_PROCESS_NAME,@Value(ProcessName),EX_ID,@Value(ProcessID),EX_TYPE,INFORMATION,EX,@Value(Logg),EX_WorkSpace,$(FME_MF_DIR_USERTYPED)$(FME_MF_NAME),EX_ROT_DIRECTORY,@Value(RotDirectory)
    BLOCKING = No
    WORKSPACE_FILE = C:\dev\Datalager_procsrc\_sys\_logg.fmw
