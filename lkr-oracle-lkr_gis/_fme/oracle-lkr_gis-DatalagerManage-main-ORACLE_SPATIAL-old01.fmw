FME workspace oracle-lkr_gis-DatalagerManage-main-ORACLE_SPATIAL-old01.fmw

Parameters:
- RotDirectory = ../   # Katalogen där processen startar
- ProcessName =   # Processnamn
- Manifest =   # Manifest (export- och schema-specifikation)
- DatabaseSchema = LKR_GIS   # Databasschema (ska vara samma som anslutningsnamnet i FME)
- Datatable =
- OutputDirectory = C:\LKR_GIS\Datalager_procsrc\_geodatarepo\landskrona\lkr_gis   # Katalog för lagring av del av datalager
- ProcessModulName =   # Processmodulsnamn
- IsWholeProcessRun = 1   # Är hela datalagerprocessen körd

Readers:
- ORACLE_SPATIAL_1: ORACLE_SPATIAL from $(DatabaseSchema)
- SCHEMA_FROM_TABLE_1: SCHEMA_FROM_TABLE from $(Manifest)

Writers:
- ESRISHAPE_1: ESRISHAPE to $(OutputDirectory)
- SDF3_1: SDF3 to $(OutputDirectory)

Creator
    NUM = 1
    GEOMTYPE = Geometry Object
    CREATED -> ParameterFetcher_2
ParameterFetcher_2
    ATTR_LIST = ProcessName $(ProcessName) RotDirectory $(RotDirectory)
    -> StringConcatenator_8
StringConcatenator_8
    VAL_ATTR = ProcessName_MAIN
    ACTION = Create New Attribute
    PARM_LINE = @Value(ProcessName)_MAIN
    -> UUIDGenerator_2
UUIDGenerator_2
    UUID_ATTR = ProcessID
    -> AttributeCreator_12
AttributeCreator_12
    ATTR_TABLE = SET_TO _FeatureIdMerger = 1
    -> AttributeCreator_12_OUTPUT
AttributeCreator_12_OUTPUT: Junction
    -> FeatureMerger_2 [SUPPLIER]
    -> FeatureMerger_3 [SUPPLIER]
Note: Workspace som inte används direkt, utan kallas på genom ett s.k. driver-workspace / Parametrar / Parametrarna sätts i DRIVER-skriptet programmatiskt / * [RotDirectory] Kommer från batch-processen och är obligatoriskt för alla FME-processor. / * [ProcessName] Kommer från batch-processen och är obligatoriskt för alla FME-processor. / * [Manifest] Excel-fil från ett tidigare exporterat schema anpassad med nya kolumnnamn samt vilken data som ska exporteras. Används i detta skript för att bygga upp gällande schema för resp. feature type. / * [DatabaseSchema] Informationen hämtas från schema-manifestet. / Databasschemat som tabeller ska exporteras ifrån (motsvarar FME:s dataset). Används även som alias för databasanslutning. Databasanslutningen ska ha samma namn i FME-klienten som kör skriptet. / * [Datatable] Informationen hämtas från schema-manifestet. Tabeller som ska läsas. / * [OutputDirectory] Katalogsökväg för exporterad geodata (delrepository).
LKR_GIS.GIS_V_BLADINDELNING (reader ORACLE_SPATIAL_1)
    attributes: KEY number(10,0), BLADNAMN varchar2(50), BLADKVADRANT varchar2(2), BLADTYP varchar2(5)
    -> ParameterFetcher
ParameterFetcher
    ATTR_LIST = ProcessName $(ProcessName) RotDirectory $(RotDirectory)
    -> StringConcatenator
StringConcatenator
    VAL_ATTR = ProcessName_MAIN
    ACTION = Create New Attribute
    PARM_LINE = @Value(ProcessName)_MAIN
    -> UUIDGenerator
UUIDGenerator
    UUID_ATTR = ProcessID
    -> SchemaMapper
    -> Sampler_2
SchemaMapper
    MAP_ATTRS = column_name dl_new_column_name $(FME_ASC_16)
    XLSXR_CONFIGURATION_DATASET = C:/dev/Datalager_procsrc/lkr-oracle-lkr_gis/_schema/schema-manifest.xlsx
    TABLE = schema
    IDXSOURCECOL = ""
    FORMAT = XLSXR
    XLSXR_FORCE_DATETIME = NO
    XLSXR_EXPAND_MERGED_CELLS = Yes
    XLSXR_QUERY_FEATURE_TYPES_FOR_MERGE_FILTERS = Yes
    XLSXR_CASE_SENSITIVE_FEATURE_TYPES = YES
    DATASET = C:\dev\Datalager_procsrc\lkr-oracle-lkr_gis\_schema\schema-manifest.xlsx
    XLSXR_ALLOW_DOLLAR_SIGNS = YES
    XLSXR_SCAN_SCHEMA_IF_DYNAMIC = No
    XLSXR_READ_BLANK_AS = Missing
    IDXDESTCOL = ""
    XLSXR_USE_SCHEMA_OTHER_FILES = No
    IDXSOURCEATTR = fme_feature_type
    XLSXR_EXCEL_COL_NAMES = YES
    XLSXR_TABLELIST = schema
    XLSXR_SCHEMA = schema,0,fme_feature_type_name,char,20,,,1,column_name,char,16,,,2,dl_need_new_column_name,char,6,,,3,dl_new_column_name,char,12,,,4,dl_export,char,5,,,5,fme_data_type,char,18,,,6,native_data_type,char,14,,,7,fme_format_long_name,char,22,,,8,fme_format_short_name,char,15,,,9,_dirpath,char,1,,,10,_extension,char,1,,,11,DatasetFull,char,8,,,12,Dataset,char,8,,,13,column_name_char_length,number,3," 0",,1,,,,NO,NO,1,C:/dev/Datalager_procsrc/lkr-oracle-lkr_gis/_schema/schema-manifest.xlsx,"0,0,13,22",,NO
    ROW_ID_ATTR = _schemamapper_row_ids
    IDXDESTATTR = fme_feature_type
    MAPPED -> AttributeCreator
    MAPPED -> GeometryFilter
AttributeCreator
    ATTR_TABLE = SET_TO DatasetName = @Value(fme_feature_type)
    -> StringCaseChanger_2
StringCaseChanger_2
    CHANGE_TYPE = lowercase
    ATTRLIST = DatasetName
    ATTRCHOICE = Selected Attributes
    -> FeatureClass1 (writer SDF3_1)
Note: : lkr_gis [SDF3]
FeatureClass1 (writer SDF3_1)
GeometryFilter
    GEOM_PORT_NAMES = Point Line Arc Area Ellipse Text Raster "Point Cloud" Surface Solid Collection Null Instance
    BREAK_AGG = No
    POINT -> StringConcatenator_4
    LINE -> StringConcatenator_5
    ARC -> StringConcatenator_5
    AREA -> StringConcatenator_6
    ELLIPSE -> StringConcatenator_6
    TEXT -> StringConcatenator_7
    RASTER -> GeometryFilter_RASTER
    POINTCLOUD -> GeometryFilter_RASTER
    SURFACE -> GeometryFilter_RASTER
    SOLID -> GeometryFilter_RASTER
    COLLECTION -> GeometryFilter_RASTER
    NULL -> GeometryFilter_RASTER
    INSTANCE -> GeometryFilter_RASTER
    <UNFILTERED> -> GeometryFilter_RASTER
StringConcatenator_4
    VAL_ATTR = DatasetName
    ACTION = Create New Attribute
    PARM_LINE = @Value(fme_feature_type)_p
    -> Junction
StringConcatenator_5
    VAL_ATTR = DatasetName
    ACTION = Create New Attribute
    PARM_LINE = @Value(fme_feature_type)_l
    -> Junction
StringConcatenator_6
    VAL_ATTR = DatasetName
    ACTION = Create New Attribute
    PARM_LINE = @Value(fme_feature_type)_y
    -> Junction
StringConcatenator_7
    VAL_ATTR = DatasetName
    ACTION = Create New Attribute
    PARM_LINE = @Value(fme_feature_type)_t
    -> Junction
Junction
    -> StringCaseChanger
StringCaseChanger
    CHANGE_TYPE = lowercase
    ATTRLIST = DatasetName
    ATTRCHOICE = Selected Attributes
    -> Shapefile10000 (writer ESRISHAPE_1)
Note: : lkr_gis [ESRISHAPE]
Shapefile10000 (writer ESRISHAPE_1)
GeometryFilter_RASTER: Junction
    -> Aggregator

Bookmark: Loggning
Aggregator
    SEP = ,
    ACCUM_ATTRS_NAME = Use Attributes From One Feature
    MODE = Geometry - Assemble One Level
    ORDERED = No
    GROUP_BY = fme_feature_type
    AGGREGATE_TYPE = Homogeneous Collection (If Possible)
    AGGREGATE -> Aggregator_3
Aggregator_3
    SEP = ", "
    COUNT_ATTR = Antal
    CONCAT_ATTRS = fme_feature_type
    ACCUM_ATTRS_NAME = Use Attributes From One Feature
    MODE = Geometry - Assemble One Level
    ORDERED = No
    AGGREGATE_TYPE = Homogeneous Collection (If Possible)
    AGGREGATE -> AttributeCreator_2
AttributeCreator_2
    ATTR_TABLE = SET_TO _FeatureIdMerger = 1
    -> FeatureMerger_3 [REQUESTOR]
FeatureMerger_3
    REJECT_NULL_MISSING_KEYS = No
    ATTR_ACCUM_MODE = Merge Supplier
    IGNORE_NULLS = No
    PROCESS_DUPS = No
    ATTR_CONFLICT_RES = Use Requestor
    SUPPLIERS_FIRST = No
    JOIN_KEYS = @Value(_FeatureIdMerger) @Value(_FeatureIdMerger) AUTO
    MERGE_TYPE = Attributes Only
    MERGED -> StringConcatenator_3
StringConcatenator_3
    VAL_ATTR = Logg
    ACTION = Create New Attribute
    PARM_LINE = Geometrier från objektklasser (@Value(fme_feature_type)) skrivs ej till shape-filer.
    -> TimeStamper_3
TimeStamper_3
    FMT = ^Y-^m-^d ^H:^M:^S
    TIME_ATTR = Timestamp
    -> Logg_3
Logg_3: WorkspaceRunner
    WORKSPACE_FILE = C:\dev\Datalager_procsrc\_sys\_logg.fmw
    BLOCKING = No
    WORKSPACE_PARAMETERS = EX_DATE_TIME,@Value(Timestamp),EX_PROCESS_NAME,@Value(ProcessName_MAIN),EX_ID,@Value(ProcessID),EX_TYPE,VARNING,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: Endast till för som signal att starta logg
Sampler_2
    SAMPLE_TYPE_LONG = First N Features
    RATE = 1
    SAMPLE_MODE = No
    SAMPLED -> AttributeCreator_13
AttributeCreator_13
    ATTR_TABLE = SET_TO _FeatureIdMerger = 1
    -> FeatureMerger_2 [REQUESTOR]
FeatureMerger_2
    REJECT_NULL_MISSING_KEYS = No
    ATTR_ACCUM_MODE = Merge Supplier
    IGNORE_NULLS = No
    PROCESS_DUPS = No
    ATTR_CONFLICT_RES = Use Requestor
    SUPPLIERS_FIRST = No
    JOIN_KEYS = @Value(_FeatureIdMerger) @Value(_FeatureIdMerger) AUTO
    MERGE_TYPE = Attributes Only
    MERGED -> StringConcatenator_2
StringConcatenator_2
    VAL_ATTR = Logg
    ACTION = Create New Attribute
    PARM_LINE = Kör @Value(ProcessName_MAIN) för data "$(DatabaseSchema).$(Datatable)" till datalagret.
    -> TimeStamper_2
TimeStamper_2
    FMT = ^Y-^m-^d ^H:^M:^S
    TIME_ATTR = Timestamp
    -> Logg_2
Logg_2: WorkspaceRunner
    WORKSPACE_FILE = C:\dev\Datalager_procsrc\_sys\_logg.fmw
    BLOCKING = No
    WORKSPACE_PARAMETERS = EX_DATE_TIME,@Value(Timestamp),EX_PROCESS_NAME,@Value(ProcessName_MAIN),EX_ID,@Value(ProcessID),EX_TYPE,INFORMATION,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
