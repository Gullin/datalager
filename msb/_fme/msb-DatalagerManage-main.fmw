FME workspace msb-DatalagerManage-main.fmw

Parameters:
- DestDataset_POSTGIS =
- DestDataset_POSTGIS_14 =
- FEATURE_TYPES =
- FME_USER_PARAM_PRIVATE_GRP =
- InData =
- IsWholeProcessRun =
- Klippytor =
- Manifest =
- OutputDirectory =
- PG_SCHEMA =
- ProcessModulName =
- ProcessName =
- RotDirectory =
- SchemaFlush =

Readers:
- FFS_1: FFS from $(Klippytor)
- XLSXR_1: XLSXR from $(Manifest)
- ESRISHAPE_1: ESRISHAPE from $(InData)

Writers:
- SDF3_1: SDF3 to $(OutputDirectory) in EPSG:3008
- SHAPEFILE_1: SHAPEFILE to $(OutputDirectory) in EPSG:3008
- POSTGIS_1: POSTGIS to $(DestDataset_POSTGIS) in EPSG:3008
- POSTGIS_2: POSTGIS to $(DestDataset_POSTGIS_14) in EPSG:3008

Note: Workspace som inte används direkt, utan kallas på genom ett s.k. driver-workspace / Parametrar / Parametrarna sätts i DRIVER-skriptet programmatiskt / * [RotDirectory] Kommer från batch-processen och är obligatoriskt för alla FME-processor. / * [ProcessName] Kommer från batch-processen och är obligatoriskt för alla FME-processor. / * [Manifest] Excel-fil från ett tidigare exporterat schema anpassad med nya kolumnnamn samt vilken data som ska exporteras. Används i detta skript för att bygga upp gällande schema för resp. feature type. / * [OutputDirectory] Katalogsökväg för exporterad geodata (delrepository). / * [ProcessModulName] / * [IsWholeProcesRun]
KlippytorSweref99TM1330 (reader FFS_1)
    attributes: Projektion varchar(200), Namn varchar(200)
    -> TestFilter
TestFilter
    DEFAULT_VALUE = <UNFILTERED>
    TEST_LIST:
      BOOL_OP,AND,COMPOSITE_TEST,<Unused>,TEST_CLAUSE,"TEST @Value(Namn) = Landskrona
      TEST @Value(Projektion) = SW99TM",Landskrona-SW99TM
    Landskrona-SW99TM -> Bufferer
Note: Klipper totalt 1,5 km utanför kommungräns. / Buffrar med 1445 m eftersom standardklippytan / är 5 m utanför kommungräns.
Bufferer
    ANGLE = 22.5
    CAP_STYLE = Arc
    CORNER_STYLE = Arc
    MODE = AREA
    OFFSET = 1445
    OFFSET_UNITS = NONE
    PRECISION = APPROX
    BUFFERED -> Clipper [CLIPPER]
DVO_polygon (reader ESRISHAPE_1)
    attributes: NVRID char(254), NAMN char(254), SKYDDSTYP char(254), BESLSTATUS char(254), URSBESLDAT date, IKRAFTDATF date, URSGALLDAT date, SENGALLDAT date, TILLSYNSMH char(254), PROVNMHDIS char(254), PROVNMHTIL char(254), LAN char(254), KOMMUN char(254), IUCNKAT char(254), FORVALTARE char(254), AREA_HA number(200,15), LAND_HA number(200,15), VATTEN_HA number(200,10), SKOG_HA number(200,10), GEOSTATUS char(254), DIARIENR char(254), LAGRUM char(254), BESLMYND char(254)
    -> ParameterFetcher
ParameterFetcher
    ATTR_LIST = ProcessName $(ProcessName) RotDirectory $(RotDirectory)
    -> StringConcatenator
StringConcatenator
    ACTION = Create New Attribute
    PARM_LINE = @Value(ProcessName)_MAIN
    VAL_ATTR = ProcessName_MAIN
    -> UUIDGenerator
UUIDGenerator
    UUID_ATTR = ProcessID
    -> Clipper [CLIPPEE]
    -> Sampler_2
Clipper
    BOUNDARY_CASES = Treat as Inside
    CLEANING_TOLERANCE = None
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> SchemaMapper
    <REJECTED> -> Aggregator_5
SchemaMapper
    DATASET = $(Manifest)
    FORMAT = XLSXR
    IDXDESTATTR = fme_feature_type
    IDXDESTCOL = ""
    IDXSOURCEATTR = fme_feature_type
    IDXSOURCECOL = ""
    MAP_ATTRS = column_name dl_new_column_name $(FME_ASC_16)
    ROW_ID_ATTR = _schemamapper_row_ids
    TABLE = schema
    XLSXR_ALLOW_DOLLAR_SIGNS = YES
    XLSXR_CASE_SENSITIVE_FEATURE_TYPES = YES
    XLSXR_CONFIGURATION_DATASET = $(Manifest)
    XLSXR_CREATE_FEATURE_TABLES_FROM_DATA = Yes
    XLSXR_EXCEL_COL_NAMES = YES
    XLSXR_EXPAND_MERGED_CELLS = Yes
    XLSXR_FORCE_DATETIME = NO
    XLSXR_KEEP_SCHEMA_SETTINGS = YES
    XLSXR_QUERY_FEATURE_TYPES_FOR_MERGE_FILTERS = Yes
    XLSXR_READ_BLANK_AS = Missing
    XLSXR_READ_RASTER_MODE = None
    XLSXR_SCAN_SCHEMA_IF_DYNAMIC = No
    XLSXR_SCHEMA = schema,0,filter_fme_feature_type,char,17,,,1,filter_export_column,char,10,,,2,fme_feature_type_name,char,26,,,3,column_name,char,11,,,4,dl_need_new_column_name,char,6,,,5,dl_new_column_name,char,11,,,6,dl_export,char,5,,,7,fme_data_type,char,20,,,8,native_data_type,char,15,,,9,fme_format_long_name,char,15,,,10,fme_format_short_name,char,10,,,11,_dirpath,char,80,,,12,_extension,char,4,,,13,DatasetFull,char,30,,,14,Dataset,char,26,,,15,column_name_char_length,number,3," 0",,1,,,,NO,NO,1,$(Manifest),"0,0,15,1714",,NO,NO
    XLSXR_STRIP_SHEETNAME_SPACES = YES
    XLSXR_TABLELIST = schema
    XLSXR_TRIM_ATTR_NAME_WHITESPACE = Yes
    XLSXR_USE_SCHEMA_OTHER_FILES = No
    MAPPED -> FeatureMerger [REQUESTOR]
    UNMAPPED -> Aggregator_6
schema (reader XLSXR_1)
    attributes: filter_fme_feature_type char(17), filter_export_column char(10), fme_feature_type_name char(60), column_name char(11), dl_need_new_column_name char(6), dl_new_column_name char(11), dl_export char(6), fme_data_type char(18), native_data_type char(11), fme_format_long_name char(15), fme_format_short_name char(14), _dirpath char(70), _extension char(5), DatasetFull char(15), Dataset char(10), column_name_char_length number(3,0)
    -> Tester
Tester
    BOOL_OP = OR
    COMPOSITE_TEST = 1
    TEST_CLAUSE = TEST @Value(dl_export) = true
    TEST_MODE = TEST
    PASSED -> AttributeManager
AttributeManager
    ATTR_TABLE:
      REMOVE filter_fme_feature_type
      REMOVE filter_export_column
      REMOVE column_name
      REMOVE dl_need_new_column_name
      RENAME_SET_VALUE dl_new_column_name > name
      REMOVE dl_export
      REMOVE _dirpath
      REMOVE _extension
      REMOVE DatasetFull
      REMOVE Dataset
      REMOVE column_name_char_length
    -> Aggregator_2
Aggregator_2
    ACCUM_ATTRS_NAME = Use Attributes From One Feature
    AGGREGATE_TYPE = Homogeneous Collection (If Possible)
    COUNT_ATTR = Antal
    GROUP_BY = fme_feature_type fme_feature_type_name fme_format_long_name fme_format_short_name
    LIST_ATTRS_TO_INCLUDE = fme_data_type name native_data_type
    LIST_NAME = attribute
    MODE = Geometry - Assemble One Level
    SEP = ,
    AGGREGATE -> AttributeKeeper_2
AttributeKeeper_2
    CREATE_BULK_MODE_FEATURES = NO
    KEEP_ATTRS = fme_feature_type_name,fme_format_long_name,fme_format_short_name
    KEEP_LIST = attribute{}
    -> FeatureMerger [SUPPLIER]
FeatureMerger
    ATTR_ACCUM_MODE = Merge Supplier
    ATTR_CONFLICT_RES = Use Requestor
    IGNORE_NULLS = No
    JOIN_KEYS = @Value(fme_feature_type) @Value(fme_feature_type_name) AUTO
    MERGE_TYPE = Attributes Only
    PROCESS_DUPS = NO
    REJECT_NULL_MISSING_KEYS = No
    SUPPLIERS_FIRST = No
    MERGED -> GtransReprojector
    UNMERGED_REQUESTOR -> Aggregator_8
GtransReprojector
    INTERPOLATION_TYPE_NAME = Nearest Neighbor
    RASTER_CELL_SIZE = Square Cells
    RASTER_TOLERANCE = 0.0
    TRANSLATION_FILE = $(FME_HOME)Reproject\Gtrans\Sys\SW99TM-1330.tf
    REPROJECTED -> AttributeCreator
AttributeCreator
    ATTR_TABLE = SET_TO _name_extension
    -> ArcStroker
Note: ArcStroker [ArcStroker] / General: / Stroke By: Maximum Deviation / Maximum Deviation: 0.02 / Make Polygon Out of 360 Degree Arcs: No
ArcStroker
    MAKE_POLY = No
    STROKE_CHOICE = Maximum Deviation
    TOLERANCE_VAL = 0.02
    STROKED -> 2DForcer
2DForcer
    2D -> GeometryRefiner
GeometryRefiner
    -> GeometryFilter
GeometryFilter
    BREAK_AGG = No
    GEOM_PORT_NAMES = Point Line Arc Area Ellipse Text Raster "Point Cloud" Surface Solid Collection Null Instance
    POINT -> StringConcatenator_4
    LINE -> StringConcatenator_5
    ARC -> StringConcatenator_31
    AREA -> StringConcatenator_6
    ELLIPSE -> StringConcatenator_32
    TEXT -> StringConcatenator_7
    RASTER -> Junction_6
    POINTCLOUD -> Junction_6
    SURFACE -> Junction_6
    SOLID -> Junction_6
    COLLECTION -> Junction_6
    NULL -> Junction_6
    INSTANCE -> Junction_6
    <UNFILTERED> -> Junction_6
StringConcatenator_4
    ACTION = Create New Attribute
    PARM_LINE = @Value(fme_feature_type)@Value(_name_extension)_p
    VAL_ATTR = DatasetName
    -> StringCaseChanger_5
StringConcatenator_5
    ACTION = Create New Attribute
    PARM_LINE = @Value(fme_feature_type)@Value(_name_extension)_l
    VAL_ATTR = DatasetName
    -> StringCaseChanger_2
StringConcatenator_31
    ACTION = Create New Attribute
    PARM_LINE = @Value(fme_feature_type)@Value(_name_extension)_l
    VAL_ATTR = DatasetName
    -> StringCaseChanger_3
StringConcatenator_6
    ACTION = Create New Attribute
    PARM_LINE = @Value(fme_feature_type)@Value(_name_extension)_y
    VAL_ATTR = DatasetName
    -> StringCaseChanger_4
StringConcatenator_32
    ACTION = Create New Attribute
    PARM_LINE = @Value(fme_feature_type)@Value(_name_extension)_y
    VAL_ATTR = DatasetName
    -> StringCaseChanger_6
StringConcatenator_7
    ACTION = Create New Attribute
    PARM_LINE = @Value(fme_feature_type)@Value(_name_extension)_t
    VAL_ATTR = DatasetName
    -> StringCaseChanger_5
Junction
    -> schema (writer POSTGIS_1)
    -> Table1 (writer POSTGIS_2)
    -> Shapefile1 (writer SHAPEFILE_1)
Note: : [SHAPEFILE]
Shapefile1 (writer SHAPEFILE_1)
Junction_6
    -> Aggregator
Creator
    GEOMTYPE = Geometry Object
    NUM = 1
    CREATED -> ParameterFetcher_2
ParameterFetcher_2
    ATTR_LIST = ProcessName $(ProcessName) RotDirectory $(RotDirectory)
    -> StringConcatenator_8
StringConcatenator_8
    ACTION = Create New Attribute
    PARM_LINE = @Value(ProcessName)_MAIN
    VAL_ATTR = ProcessName_MAIN
    -> UUIDGenerator_2
UUIDGenerator_2
    UUID_ATTR = ProcessID
    -> AttributeCreator_12_OUTPUT
AttributeCreator_12_OUTPUT: Junction
    -> FeatureMerger_2 [SUPPLIER]
    -> FeatureMerger_3 [SUPPLIER]
    -> FeatureMerger_4 [SUPPLIER]
    -> FeatureMerger_5 [SUPPLIER]
    -> FeatureMerger_6 [SUPPLIER]
    -> FeatureMerger_7 [SUPPLIER]

Bookmark: Loggning
Aggregator_6
    ACCUM_ATTRS_NAME = Use Attributes From One Feature
    AGGREGATE_TYPE = Homogeneous Collection (If Possible)
    GROUP_BY = fme_feature_type
    MODE = Geometry - Assemble One Level
    SEP = ", "
    AGGREGATE -> Aggregator_7
Aggregator_7
    ACCUM_ATTRS_NAME = Use Attributes From One Feature
    AGGREGATE_TYPE = Homogeneous Collection (If Possible)
    CONCAT_ATTRS = fme_feature_type
    MODE = Geometry - Assemble One Level
    SEP = ", "
    AGGREGATE -> FeatureMerger_6 [REQUESTOR]
Aggregator_5
    ACCUM_ATTRS_NAME = Use Attributes From One Feature
    AGGREGATE_TYPE = Homogeneous Collection (If Possible)
    COUNT_ATTR = Antal
    MODE = Geometry - Assemble One Level
    SEP = ", "
    AGGREGATE -> FeatureMerger_5 [REQUESTOR]
Note: Endast till för som signal att starta logg
Sampler_2
    RATE = 1
    SAMPLE_MODE = No
    SAMPLE_TYPE_LONG = First N Features
    SAMPLED -> FeatureMerger_2 [REQUESTOR]
Junction_2
    -> Aggregator_4
Aggregator_4
    ACCUM_ATTRS_NAME = Use Attributes From One Feature
    AGGREGATE_TYPE = Homogeneous Collection (If Possible)
    COUNT_ATTR = Antal
    MODE = Geometry - Assemble One Level
    SEP = ", "
    AGGREGATE -> FeatureMerger_4 [REQUESTOR]
Aggregator
    ACCUM_ATTRS_NAME = Use Attributes From One Feature
    AGGREGATE_TYPE = Homogeneous Collection (If Possible)
    GROUP_BY = fme_feature_type
    MODE = Geometry - Assemble One Level
    SEP = ,
    AGGREGATE -> Aggregator_3
Aggregator_3
    ACCUM_ATTRS_NAME = Use Attributes From One Feature
    AGGREGATE_TYPE = Homogeneous Collection (If Possible)
    CONCAT_ATTRS = fme_feature_type
    COUNT_ATTR = Antal
    MODE = Geometry - Assemble One Level
    SEP = ", "
    AGGREGATE -> FeatureMerger_3 [REQUESTOR]
Aggregator_8
    ACCUM_ATTRS_NAME = Use Attributes From One Feature
    AGGREGATE_TYPE = Homogeneous Collection (If Possible)
    GROUP_BY = fme_feature_type
    MODE = Geometry - Assemble One Level
    SEP = ", "
    AGGREGATE -> Aggregator_9
Aggregator_9
    ACCUM_ATTRS_NAME = Use Attributes From One Feature
    AGGREGATE_TYPE = Homogeneous Collection (If Possible)
    CONCAT_ATTRS = fme_feature_type
    MODE = Geometry - Assemble One Level
    SEP = ", "
    AGGREGATE -> FeatureMerger_7 [REQUESTOR]
FeatureMerger_5
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_10
StringConcatenator_10
    ACTION = Create New Attribute
    PARM_LINE = @Value(Antal)st. objekt avslogs att klippas med transformern Clipper.
    VAL_ATTR = Logg
    -> DTStamperYYYY-MM-DD_HH:MI:SS.sss_2
DTStamperYYYY-MM-DD_HH:MI:SS.sss_2
    -> Logg_5
Logg_5: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,VARNING,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_3
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_3
StringConcatenator_3
    ACTION = Create New Attribute
    PARM_LINE = Geometrier från objektklasser (@Value(fme_feature_type)) skrivs ej till shape-filer.
    VAL_ATTR = Logg
    -> DTStamperYYYY-MM-DD_HH:MI:SS.sss_3
DTStamperYYYY-MM-DD_HH:MI:SS.sss_3
    -> Logg_3
Logg_3: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,VARNING,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_9
StringConcatenator_9
    ACTION = Create New Attribute
    PARM_LINE = @Value(ProcessName_MAIN) avslutad med @Value(Antal) st. objekt skrivna till datalagret.
    VAL_ATTR = Logg
    -> DTStamperYYYY-MM-DD_HH:MI:SS.sss_4
DTStamperYYYY-MM-DD_HH:MI:SS.sss_4
    -> Logg_4
Logg_4: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,KLART,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_2
StringConcatenator_2
    ACTION = Create New Attribute
    PARM_LINE = Kör @Value(ProcessName_MAIN) för data i "$(Manifest)" till datalagret.
    VAL_ATTR = Logg
    -> DTStamperYYYY-MM-DD_HH:MI:SS.sss
DTStamperYYYY-MM-DD_HH:MI:SS.sss
    -> Logg_2
Logg_2: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,INFORMATION,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_6
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_11
StringConcatenator_11
    ACTION = Create New Attribute
    PARM_LINE = fme_basicstring:37%24%31:Kolumner och dess namn i dataset(en) @Value(fme_feature_type) har ej länkats till nytt namn.
    VAL_ATTR = Logg
    -> DTStamperYYYY-MM-DD_HH:MI:SS.sss_5
DTStamperYYYY-MM-DD_HH:MI:SS.sss_5
    -> Logg_6
Logg_6: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_7
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_12
StringConcatenator_12
    ACTION = Create New Attribute
    PARM_LINE = fme_basicstring:12%24%180:Dataset(en) @Value(fme_feature_type) har ej länkats till något schema. Kommer ej att kunna skapas med attribut. Kontrollera anledningen till att dataset åkt igenom utan upptagning på korrekt sätt i schemahanteringen.
    VAL_ATTR = Logg
    -> DTStamperYYYY-MM-DD_HH:MI:SS.sss_6
DTStamperYYYY-MM-DD_HH:MI:SS.sss_6
    -> Logg_7
Logg_7: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)

Bookmark: FDO_Line
StringCaseChanger_2
    ATTRCHOICE = Selected Attributes
    ATTRLIST = DatasetName
    CHANGE_TYPE = lowercase
    -> FeatureClass10000 (writer SDF3_1)
    -> Junction_2
    -> Junction
Note: : lkr_gis [SDF3] Line
FeatureClass10000 (writer SDF3_1)

Bookmark: FDO_Arc
StringCaseChanger_3
    ATTRCHOICE = Selected Attributes
    ATTRLIST = DatasetName
    CHANGE_TYPE = lowercase
    -> FeatureClass10001 (writer SDF3_1)
    -> Junction_2
    -> Junction
Note: : lkr_gis [SDF3] Arc
FeatureClass10001 (writer SDF3_1)

Bookmark: FDO_Area
StringCaseChanger_4
    ATTRCHOICE = Selected Attributes
    ATTRLIST = DatasetName
    CHANGE_TYPE = lowercase
    -> FeatureClass10002 (writer SDF3_1)
    -> Junction_2
    -> Junction
Note: : lkr_gis [SDF3] Area
FeatureClass10002 (writer SDF3_1)

Bookmark: FDO_Ellipse
StringCaseChanger_6
    ATTRCHOICE = Selected Attributes
    ATTRLIST = DatasetName
    CHANGE_TYPE = lowercase
    -> FeatureClass10003 (writer SDF3_1)
    -> Junction_2
    -> Junction
Note: : lkr_gis [SDF3] Ellipse
FeatureClass10003 (writer SDF3_1)

Bookmark: FDO_Point
StringCaseChanger_5
    ATTRCHOICE = Selected Attributes
    ATTRLIST = DatasetName
    CHANGE_TYPE = lowercase
    -> FeatureClass100 (writer SDF3_1)
    -> Junction_2
    -> Junction
Note: : lkr_gis [SDF3] Point
FeatureClass100 (writer SDF3_1)

Bookmark: PostGIS
Note: BUGG (FME 2021.0): / "Table Qualifier" i writer fungerar inte med dynamisk skrivning. Värdet behöver konkatineras i "Table Name"
schema (writer POSTGIS_1)
Table1 (writer POSTGIS_2)

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    INCLUDE_OFFSET = NO
    STAMP_TYPE = datetime
    TIMEZONE = local
    -> DateTimeConverter
DateTimeConverter
    DATETIME_ATTR = _dts
    OUT_FORMAT = %Y-%m-%d %H:%M:%S
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    NO_MATCH = _FME_NO_OP_
    REGEXP = YES
    SRC_ATTRS = _dts
    -> StringReplacer_2
StringReplacer_2
    CASE = NO
    FIND_TEXT = .*\.
    NO_MATCH = _FME_NO_OP_
    REGEXP = YES
    SRC_ATTRS = _mils
    -> SubstringExtractor
SubstringExtractor
    END = 2
    RESULT_ATTR = _subMils
    SRC_STRING = @Value(_mils)
    START = 0
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)
