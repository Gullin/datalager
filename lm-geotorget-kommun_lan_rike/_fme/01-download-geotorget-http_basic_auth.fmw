FME workspace 01-download-geotorget-http_basic_auth.fmw

Parameters:
- RotDirectory = ../   # Katalogen där processen startar
- ProcessName =   # Processnamn
- OutputDirectory = ../   # Katalog för lagring av nedladdat
- ProcessModulName =   # Processmodulsnamn
- IsWholeProcessRun = 1   # Är hela datalagerprocessen körd
- FME_USER_PARAM_PRIVATE_GRP =   # Private Parameters
- FeatureListFile = _modul-settings-datasets.ini   # Fil med listade features
- USERNAME =   # Lantmäteriets funktionskonto
- PASSWORD =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   # Lösenord

Creator
    GEOMTYPE = Geometry Object
    NUM = 1
    CREATED -> ParameterFetcher
ParameterFetcher
    ATTR_LIST = _PASSWORD $(PASSWORD) _USERNAME $(USERNAME) _RotDirectory $(RotDirectory) _ProcessModulName $(ProcessModulName)
    -> UUIDGenerator_2
UUIDGenerator_2
    UUID_ATTR = ProcessID
    -> FeatureReader_2 [INITIATOR]
    -> StringConcatenator_13
FeatureReader_2
    ATTR_ACCUM_MODE = Only Use Result
    COMBINE_GEOM = Use Result
    CSV2_CASE_SENSITIVE_FIELD_NAMES = Yes
    CSV2_CHUNK_SIZE = 100000
    CSV2_DATA_START_LINE = 1
    CSV2_DELIMITER = |
    CSV2_ENCODING = ibm437
    CSV2_ENFORCE_STRICT_SCHEMA = No
    CSV2_FEATURE_TYPE_NAME = FORMAT_NAME
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 1000
    CSV2_SCAN_TYPES = No
    CSV2_SKIP_DUPLICATE_DELIMITERS = No
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = NO
    DATASET = $(RotDirectory)$(ProcessName)/_schema/$(FeatureListFile)
    FORMAT = CSV2
    INTERACT = <No Spatial Filter>
    OUTPUT_FEATURES_DISPLAY = Data Features
    <OTHER> -> AttributeExposer
    INITIATOR -> FeatureMerger_4 [REQUESTOR]
    <REJECTED> -> Aggregator_5
AttributeExposer
    ATTR_LIST = col0,col1,col2,col3,col4
    -> FeatureMerger_4 [SUPPLIER]
FeatureMerger_4
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = 1 1 AUTO
    LIST_NAME = _dataPackages
    MERGE_TYPE = Attributes Only
    PROCESS_DUPS = YES
    REJECT_NULL_MISSING_KEYS = No
    SUPPLIERS_FIRST = No
    MERGED -> ListExploder_2
    <REJECTED> -> Aggregator_2
ListExploder_2
    ATTR_ACCUM_MODE = Merge List Attributes
    ATTR_CONFLICT_RES = Use List Attribute Values
    LIST_ATTR = _dataPackages{}
    ELEMENTS -> Tester_3
    <REJECTED> -> Aggregator_11
Note: Plockar bort kommentarer och tomma rader
Tester_3
    BOOL_OP = COMPOSITE
    COMPOSITE_TEST = "1 OR ((2 OR 3) AND (4 OR 5 OR 6) AND (7 OR 8 OR 9) AND (10 OR 11 OR 12))"
    TEST_CLAUSE:
      TEST @Value(col0) BEGINS_WITH ;
      TEST col0 ATTRIBUTE_VALUE_NULL ""
      TEST col0 ATTRIBUTE_IS_EMPTY ""
      TEST col1 ATTRIBUTE_VALUE_NULL ""
      TEST col1 ATTRIBUTE_IS_EMPTY ""
      TEST col1 ATTRIBUTE_IS_MISSING ""
      TEST col2 ATTRIBUTE_VALUE_NULL ""
      TEST col2 ATTRIBUTE_IS_EMPTY ""
      TEST col2 ATTRIBUTE_IS_MISSING ""
      TEST col3 ATTRIBUTE_VALUE_NULL ""
      TEST col3 ATTRIBUTE_IS_EMPTY ""
      TEST col3 ATTRIBUTE_IS_MISSING ""
    TEST_MODE = Automatic
    FAILED -> StringReplacer_3
StringReplacer_3
    CASE = NO
    FIND_TEXT = /**/*.gpkg
    NO_MATCH = _FME_NO_OP_
    REGEXP = NO
    SRC_ATTRS = col0
    -> StringConcatenator_6
StringConcatenator_6
    ACTION = Create New Attribute
    PARM_LINE = fme_basicstring:12%12:@Value(col1)@Value(col0)
    VAL_ATTR = _request_url
    -> StringConcatenator_4
StringConcatenator_4
    ACTION = Create New Attribute
    PARM_LINE = fme_basicstring:18%1%12:$(OutputDirectory)/@Value(col0)
    VAL_ATTR = _response_url
    -> HTTPCaller_2
HTTPCaller_2
    AUTH_METHOD = Basic
    AUTH_PASSWORD = @Value(_PASSWORD)
    AUTH_USERNAME = @Value(_USERNAME)
    CONNECTION_TIMEOUT_LENGTH = 60
    ERROR_ATTR = _error
    FILE_PATH_ATTR = _response_file_path
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    OUTPUT_FILENAME = @Value(_response_url)
    REDIRECT_AUTH = ORIGINAL_DOMAIN_ONLY
    RESPONSE_TYPE = File
    STATUS_CODE_ATTR = _http_status_code
    TARGET_URL = @Value(_request_url)
    TRANSFER_TIMEOUT_LENGTH = 90
    USE_COOKIES = No
    VERIFY_SSL_CERTIFICATES = Yes
    -> Tester
    <REJECTED> -> Aggregator_21
Tester
    BOOL_OP = OR
    TEST_CLAUSE = TEST @Value(_http_status_code) = 200
    TEST_MODE = TEST
    PASSED -> Aggregator_3
    FAILED -> StringConcatenator

Bookmark: Loggning
Aggregator_3
    ACCUM_ATTRS_NAME = Use Attributes From One Feature
    AGGREGATE_TYPE = Homogeneous Collection (If Possible)
    CONCAT_ATTRS = _request_url
    COUNT_ATTR = Antal
    MODE = Geometry - Assemble One Level
    SEP = "\n"
    AGGREGATE -> FeatureMerger_7 [REQUESTOR]
StringConcatenator
    ACTION = Create New Attribute
    PARM_LINE = fme_basicstring:20%17%25%1:@Value(_request_url) (http-statuskod @Value(_http_status_code))
    VAL_ATTR = _request_result
    -> Aggregator
Aggregator
    ACCUM_ATTRS_NAME = Use Attributes From One Feature
    AGGREGATE_TYPE = Homogeneous Collection (If Possible)
    CONCAT_ATTRS = _request_result
    COUNT_ATTR = Antal
    MODE = Geometry - Assemble One Level
    SEP = "\n"
    AGGREGATE -> FeatureMerger_5 [REQUESTOR]
Aggregator_21
    ACCUM_ATTRS_NAME = Use Attributes From One Feature
    AGGREGATE_TYPE = Homogeneous Collection (If Possible)
    GROUP_BY = _http_status_code _error _request_url
    MODE = Geometry - Assemble One Level
    ORDERED = No
    SEP = ", "
    AGGREGATE -> StringConcatenator_2
StringConcatenator_2
    ACTION = Create New Attribute
    PARM_LINE:
      fme_basicstring:16%25%1%5%1%20%1%4%1%14:HTTP-statuskod: @Value(_http_status_code)
      Data:
      @Value(_request_url)
      Fel:
      @Value(_error)
    VAL_ATTR = _ErrorMessage
    -> Aggregator_22
Aggregator_22
    ACCUM_ATTRS_NAME = Use Attributes From One Feature
    AGGREGATE_TYPE = Homogeneous Collection (If Possible)
    CONCAT_ATTRS = _ErrorMessage
    MODE = Geometry - Assemble One Level
    ORDERED = No
    SEP = ", \n"
    AGGREGATE -> FeatureMerger_13 [REQUESTOR]
Aggregator_11
    ACCUM_ATTRS_NAME = Use Attributes From One Feature
    AGGREGATE_TYPE = Homogeneous Collection (If Possible)
    GROUP_BY = fme_rejection_code
    MODE = Geometry - Assemble One Level
    ORDERED = No
    SEP = ", "
    AGGREGATE -> StringConcatenator_24
StringConcatenator_24
    ACTION = Create New Attribute
    PARM_LINE = fme_basicstring:16%26%1:(FME-rejection: @Value(fme_rejection_code))
    VAL_ATTR = _ErrorMessage
    -> Aggregator_12
Aggregator_12
    ACCUM_ATTRS_NAME = Use Attributes From One Feature
    AGGREGATE_TYPE = Homogeneous Collection (If Possible)
    CONCAT_ATTRS = _ErrorMessage
    MODE = Geometry - Assemble One Level
    ORDERED = No
    SEP = ", \n"
    AGGREGATE -> FeatureMerger_8 [REQUESTOR]
Aggregator_2
    ACCUM_ATTRS_NAME = Use Attributes From One Feature
    AGGREGATE_TYPE = Homogeneous Collection (If Possible)
    GROUP_BY = fme_rejection_code
    MODE = Geometry - Assemble One Level
    ORDERED = No
    SEP = ", "
    AGGREGATE -> StringConcatenator_8
StringConcatenator_8
    ACTION = Create New Attribute
    PARM_LINE = fme_basicstring:16%26%1:(FME-rejection: @Value(fme_rejection_code))
    VAL_ATTR = _ErrorMessage
    -> Aggregator_4
Aggregator_4
    ACCUM_ATTRS_NAME = Use Attributes From One Feature
    AGGREGATE_TYPE = Homogeneous Collection (If Possible)
    CONCAT_ATTRS = _ErrorMessage
    MODE = Geometry - Assemble One Level
    ORDERED = No
    SEP = ", \n"
    AGGREGATE -> FeatureMerger_2 [REQUESTOR]
Aggregator_5
    ACCUM_ATTRS_NAME = Use Attributes From One Feature
    AGGREGATE_TYPE = Homogeneous Collection (If Possible)
    GROUP_BY = _reader_error
    MODE = Geometry - Assemble One Level
    ORDERED = No
    SEP = ", "
    AGGREGATE -> StringConcatenator_11
StringConcatenator_11
    ACTION = Create New Attribute
    PARM_LINE = fme_basicstring:16%21%1:(FME-rejection: @Value(_reader_error))
    VAL_ATTR = _ErrorMessage
    -> Aggregator_6
Aggregator_6
    ACCUM_ATTRS_NAME = Use Attributes From One Feature
    AGGREGATE_TYPE = Homogeneous Collection (If Possible)
    CONCAT_ATTRS = _ErrorMessage
    MODE = Geometry - Assemble One Level
    ORDERED = No
    SEP = ", \n"
    AGGREGATE -> FeatureMerger_3 [REQUESTOR]
StringConcatenator_13
    ACTION = Create New Attribute
    PARM_LINE = fme_basicstring:25%9:@Value(_ProcessModulName)_DOWNLOAD
    VAL_ATTR = ProcessName_DOWNLOAD
    -> AttributeCreator_6
    -> FeatureMerger_13 [SUPPLIER]
    -> FeatureMerger_8 [SUPPLIER]
    -> FeatureMerger_5 [SUPPLIER]
    -> FeatureMerger_7 [SUPPLIER]
    -> FeatureMerger_2 [SUPPLIER]
    -> FeatureMerger_3 [SUPPLIER]
FeatureMerger_3
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_10
StringConcatenator_10
    ACTION = Create New Attribute
    PARM_LINE:
      fme_basicstring:27%1%14%1%21:FeatureReader misslyckades.
      Felmeddelande:
      @Value(_ErrorMessage)
    VAL_ATTR = Logg
    -> DTStamperYYYY-MM-DD_HH:MI:SS.sss_3
DTStamperYYYY-MM-DD_HH:MI:SS.sss_3
    -> Logg_4
Logg_4: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DOWNLOAD),EX_ID,@Value(ProcessID),EX_TYPE,ERROR,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_7
StringConcatenator_7
    ACTION = Create New Attribute
    PARM_LINE:
      fme_basicstring:26%1%14%1%21:FeatureMerge misslyckades.
      Felmeddelande:
      @Value(_ErrorMessage)
    VAL_ATTR = Logg
    -> DTStamperYYYY-MM-DD_HH:MI:SS.sss_2
DTStamperYYYY-MM-DD_HH:MI:SS.sss_2
    -> Logg_3
Logg_3: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DOWNLOAD),EX_ID,@Value(ProcessID),EX_TYPE,ERROR,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
FeatureMerger_8
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_15
StringConcatenator_15
    ACTION = Create New Attribute
    PARM_LINE:
      fme_basicstring:29%1%14%1%21:Listexplodering misslyckades.
      Felmeddelande:
      @Value(_ErrorMessage)
    VAL_ATTR = Logg
    -> DTStamperYYYY-MM-DD_HH:MI:SS.sss_8
DTStamperYYYY-MM-DD_HH:MI:SS.sss_8
    -> Logg_9
Logg_9: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DOWNLOAD),EX_ID,@Value(ProcessID),EX_TYPE,ERROR,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
FeatureMerger_13
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_23
StringConcatenator_23
    ACTION = Create New Attribute
    PARM_LINE:
      fme_basicstring:23%1%21:Förfrågan misslyckades:
      @Value(_ErrorMessage)
    VAL_ATTR = Logg
    -> DTStamperYYYY-MM-DD_HH:MI:SS.sss_13
DTStamperYYYY-MM-DD_HH:MI:SS.sss_13
    -> Logg_14
Logg_14: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DOWNLOAD),EX_ID,@Value(ProcessID),EX_TYPE,ERROR,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
FeatureMerger_5
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_9
StringConcatenator_9
    ACTION = Create New Attribute
    PARM_LINE:
      fme_basicstring:28%22%13%44%1%23:@Value(ProcessName_DOWNLOAD) kunde inte ladda ner @Value(Antal) st. av följande dataset med http-statuskod
      @Value(_request_result)
    VAL_ATTR = Logg
    -> DTStamperYYYY-MM-DD_HH:MI:SS.sss_5
DTStamperYYYY-MM-DD_HH:MI:SS.sss_5
    -> Logg_6
Logg_6: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_DOWNLOAD),EX_ID,@Value(ProcessID),EX_TYPE,ERROR,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
FeatureMerger_7
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_3
StringConcatenator_3
    ACTION = Create New Attribute
    PARM_LINE:
      fme_basicstring:28%14%13%36%1%20%1:@Value(ProcessName_DOWNLOAD) avslutad med @Value(Antal) st. dataset nedladdade av följande:
      @Value(_request_url).
    VAL_ATTR = Logg
    -> DTStamperYYYY-MM-DD_HH:MI:SS.sss_6
DTStamperYYYY-MM-DD_HH:MI:SS.sss_6
    -> Logg_7
Logg_7: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DOWNLOAD),EX_ID,@Value(ProcessID),EX_TYPE,KLART,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)
AttributeCreator_6
    ATTR_TABLE = SET_TO _FileToRead = $(RotDirectory)$(ProcessName)/_schema/$(FeatureListFile)
    -> StringConcatenator_5
StringConcatenator_5
    ACTION = Create New Attribute
    PARM_LINE = fme_basicstring:4%28%13%18%2:Kör @Value(ProcessName_DOWNLOAD) för data i "$(FeatureListFile)".
    VAL_ATTR = Logg
    -> DTStamperYYYY-MM-DD_HH:MI:SS.sss
DTStamperYYYY-MM-DD_HH:MI:SS.sss
    -> Logg_2
Logg_2: WorkspaceRunner
    BLOCKING = No
    WORKSPACE_FILE = C:\dev\Datalager_procsrc\_sys\_logg.fmw
    WORKSPACE_PARAMETERS = EX_DATE_TIME,@Value(_datetimestamp),EX_PROCESS_NAME,@Value(ProcessName_DOWNLOAD),EX_ID,@Value(ProcessID),EX_TYPE,INFORMATION,EX,@Value(Logg),EX_WorkSpace,$(FME_MF_DIR_USERTYPED)$(FME_MF_NAME),EX_ROT_DIRECTORY,@Value(_RotDirectory),EX_PROCESS_MODUL_NAME,$(ProcessModulName),IsWholeProcessRun,$(IsWholeProcessRun)

FME custom transformer LantmaterietAPIAccessTokenFetcher
LantmaterietAPIAccessTokenFetcher
Generates an Access Token for API:s from Lantmäteriet, the Swedish mapping, cadastral and land registration authority.
If the token received expires too soon, it is revoked and a new token is generated.
This transformer can be used on its own to generate authentication for Lantmäteriet's API:s.
It can also be used together with the following transformers to handle downloads from the "Geotorget-Order - v2" API:
LantmaterietAPIDeliveryRequestor
LantmaterietAPIDownloadLinkFetcher
Create an Application, subscribe to the relevant API:s and generate keys for your application at:
https://apimanager.lantmateriet.se/store/
Input the application's Consumer Key and Consumer Secret as parameters.
Parameters
API_KEY
"Consumer Key" from the Application at https://apimanager.lantmateriet.se/store.
API_SECRET
"Consumer Secret" from the Application at https://apimanager.lantmateriet.se/store.
OPTIONAL_SCOPE
A single application may generate tokens for multiple scopes (e g for multiple clients). Tokens generated for a specific scope must be used along with their scopes in further requests.
API_BASE_URL
The base URL for the API endpoints, e g https://api.lantmateriet.se
API_TOKEN_URL
The API's token generation endpoint (excluding the base URL)
API_TOKEN_REVOKE_URL
The API's endpoint for revoking tokens (excluding the base URL)
MINIMUM_TOKEN_LIFETIME
Tokens with expires_in less than this number will be revoked and a new token is generated.
License
MIT License
Copyright © 2021, Mattias Spångmyr, Haninge kommun.
Permission is hereby granted, free of charge, to any person obtaining a copy
of this software and associated documentation files (the "Software"), to deal
in the Software without restriction, including without limitation the rights
to use, copy, modify, merge, publish, distribute, sublicense, and/or sell
copies of the Software, and to permit persons to whom the Software is
furnished to do so, subject to the following conditions:
The above copyright notice and this permission notice shall be included in all
copies or substantial portions of the Software.
THE SOFTWARE IS PROVIDED "AS IS", WITHOUT WARRANTY OF ANY KIND, EXPRESS OR
IMPLIED, INCLUDING BUT NOT LIMITED TO THE WARRANTIES OF MERCHANTABILITY,
FITNESS FOR A PARTICULAR PURPOSE AND NONINFRINGEMENT. IN NO EVENT SHALL THE
AUTHORS OR COPYRIGHT HOLDERS BE LIABLE FOR ANY CLAIM, DAMAGES OR OTHER
LIABILITY, WHETHER IN AN ACTION OF CONTRACT, TORT OR OTHERWISE, ARISING FROM,
OUT OF OR IN CONNECTION WITH THE SOFTWARE OR THE USE OR OTHER DEALINGS IN THE
SOFTWARE.

Parameters:
- API_KEY =   # API Consumer Key
- API_SECRET =   # API Consumer Secret
- OPTIONAL_SCOPE =   # If the application requires a scope, input the scope here
- API_AUTH_URL = https://apimanager.lantmateriet.se   # URL for LM's API Authentication
- API_TOKEN_URL = /oauth2/token   # Access Token Request URL
- API_TOKEN_REVOKE_URL = /oauth2/revoke   # Access Token Revoke Request URL
- MINIMUM_TOKEN_LIFETIME = 1800   # Minimum seconds left on token before regenerating

Note: Input features to receive the access token
Input (input)
    -> ParameterFetcher
ParameterFetcher
    ATTR_LIST = _OPTIONAL_SCOPE $(OPTIONAL_SCOPE)
    -> AttributeCreator_AuthorizationKey
RetryAfterRevokation (input)
    -> HTTPCaller_GenerateAccessToken
Note: HTTPCaller_GenerateAccessToken [HTTPCaller Version 1] / Request: / Request URL: $(API_AUTH_URL)$(API_TOKEN_URL) / HTTP Method: POST / Query String Parameters: NameValuegrant_typeclient_credentialsscope@Value(_OPTIONAL_SCOPE) Headers: NameValueAuthorizationBasic @Value(__authorizationkey) Body: / Upload Data: Specify Upload Body / Upload Body: <not set> / Content Type: Text (text/plain) / Response: / Save Response Body To: Attribute / Response Body Attribute: __response_body / Response Body Encoding: <Auto Detect from HTTP Headers> / Response Headers and Status: / List Attribute for Response Headers: <not set> / Status Code Attribute: __http_status_code / Error Attribute: __error / HTTP Client Options: / Save Cookies: No / Follow Redirects: Yes / Verify SSL Certificates: Yes / Connection Timeout Length (seconds): 60 / Transfer Timeout Length (seconds): 90 / Latest Version: 6
Note: Request a new Access Token
HTTPCaller_GenerateAccessToken
    ADDITIONAL_URL_PARAMETERS = grant_type;client_credentials scope;@Value(_OPTIONAL_SCOPE)
    CONNECTION_TIMEOUT_LENGTH = 60
    CUSTOM_HEADERS = Authorization;Basic @Value(__authorizationkey)
    ERROR_ATTR = __error
    FOLLOW_REDIRECTS = Yes
    HTTP_METHOD = POST
    SAVE_FILE = Attribute
    STATUS_CODE_ATTR = __http_status_code
    TARGET_ATTR = __response_body
    TARGET_ATTR_ENCODING = auto-detect
    TARGET_URL = $(API_AUTH_URL)$(API_TOKEN_URL)
    TRANSFER_TIMEOUT_LENGTH = 90
    UPLOAD_CONTENT_TYPE = Text (text/plain)
    UPLOAD_TYPE = Specify Upload Body
    USE_COOKIES = No
    VERIFY_SSL_CERTIFICATES = Yes
    -> JSONExtractor_Token
    <REJECTED> -> StringConcatenator_6
Note: Extract the response values
JSONExtractor_Token
    EXTRACT_QUERY_TABLE = _access_token json["access_token"] _scope json["scope"] _token_type json["token_type"] _expires_in json["expires_in"]
    JSON_DOCUMENT = @Value(__response_body)
    READ_FROM_FILE = NO
    EVALUATED -> Tester_TokenExpiresSoon
    <REJECTED> -> StringConcatenator_2
Note: Check if the token is expiring soon
Tester_TokenExpiresSoon
    BOOL_OP = OR
    TEST_CLAUSE = TEST @Value(_expires_in) < $(MINIMUM_TOKEN_LIFETIME)
    TEST_MODE = TEST
    PASSED -> HTTPCaller_RevokeAccessToken
    FAILED -> AttributeRemover_ClearUnnecessary
Note: Remove unwanted attributes
AttributeRemover_ClearUnnecessary
    REMOVE_ATTRS = __response_body,__http_status_code,__creation_instance,__authorizationkey
    -> OutputWithToken (output)
OutputWithToken (output)
Note: HTTPCaller_RevokeAccessToken [HTTPCaller Version 1] / Request: / Request URL: $(API_AUTH_URL)$(API_TOKEN_REVOKE_URL) / HTTP Method: POST / Query String Parameters: NameValuetoken@Value(_access_token) Headers: NameValueAuthorizationBasic @Value(__authorizationkey) Body: / Upload Data: Specify Upload Body / Upload Body: <not set> / Content Type: Text (text/plain) / Response: / Save Response Body To: Attribute / Response Body Attribute: __response_body / Response Body Encoding: <Auto Detect from HTTP Headers> / Response Headers and Status: / List Attribute for Response Headers: <not set> / Status Code Attribute: __http_status_code / Error Attribute: __error / HTTP Client Options: / Save Cookies: No / Follow Redirects: Yes / Verify SSL Certificates: Yes / Connection Timeout Length (seconds): 60 / Transfer Timeout Length (seconds): 90 / Latest Version: 6
Note: Revoke an old access token so that a new one can be generated.
HTTPCaller_RevokeAccessToken
    ADDITIONAL_URL_PARAMETERS = token;@Value(_access_token)
    CONNECTION_TIMEOUT_LENGTH = 60
    CUSTOM_HEADERS = Authorization;Basic @Value(__authorizationkey)
    ERROR_ATTR = __error
    FOLLOW_REDIRECTS = Yes
    HTTP_METHOD = POST
    SAVE_FILE = Attribute
    STATUS_CODE_ATTR = __http_status_code
    TARGET_ATTR = __response_body
    TARGET_ATTR_ENCODING = auto-detect
    TARGET_URL = $(API_AUTH_URL)$(API_TOKEN_REVOKE_URL)
    TRANSFER_TIMEOUT_LENGTH = 90
    UPLOAD_CONTENT_TYPE = Text (text/plain)
    UPLOAD_TYPE = Specify Upload Body
    USE_COOKIES = No
    VERIFY_SSL_CERTIFICATES = Yes
    -> RetryAfterRevokation (output)
    <REJECTED> -> StringConcatenator_3
RetryAfterRevokation (output)
<Rejected> (output)

Bookmark: Autorization Key
Note: Create and encode the authorization string from the consumer key and consumer secret
AttributeCreator_AuthorizationKey
    ATTR_TABLE = SET_TO __authorizationkey = $(API_KEY):$(API_SECRET)
    -> TextEncoder_AuthorizationKey
TextEncoder_AuthorizationKey
    DEST_ATTR = __authorizationkey
    ENCODING_TYPE = BASE64_ENCODE
    STRING_TO_ENCODE = @Value(__authorizationkey)
    -> HTTPCaller_GenerateAccessToken

Bookmark: Rejected meddelande
StringConcatenator_3
    ACTION = Create New Attribute
    PARM_LINE:
      fme_basicstring:40%1%14%1%26%1%9%1%10%1%15%1%14%1%26%1%13%1%23:Generering av access token misslyckades.
      Felmeddelande:
      @Value(fme_rejection_code)
      HTTP-fel:
      Meddelande
      @Value(__error)
      HTTP-statuskod
      @Value(__http_status_code)
      Response body
      @Value(__response_body)
    VAL_ATTR = Logg
    -> <Rejected> (output)
StringConcatenator_2
    ACTION = Create New Attribute
    PARM_LINE:
      fme_basicstring:26%1%14%1%26:JSON-parsing misslyckades.
      Felmeddelande:
      @Value(fme_rejection_code)
    VAL_ATTR = Logg
    -> <Rejected> (output)
StringConcatenator_6
    ACTION = Create New Attribute
    PARM_LINE:
      fme_basicstring:40%1%14%1%26%1%9%1%10%1%15%1%14%1%26%1%13%1%23:Generering av access token misslyckades.
      Felmeddelande:
      @Value(fme_rejection_code)
      HTTP-fel:
      Meddelande
      @Value(__error)
      HTTP-statuskod
      @Value(__http_status_code)
      Response body
      @Value(__response_body)
    VAL_ATTR = Logg
    -> <Rejected> (output)

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    INCLUDE_OFFSET = NO
    STAMP_TYPE = datetime
    TIMEZONE = local
    -> DateTimeConverter
DateTimeConverter
    DATETIME_ATTR = _dts
    OUT_FORMAT = %Y-%m-%d %H:%M:%S
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    NO_MATCH = _FME_NO_OP_
    REGEXP = YES
    SRC_ATTRS = _dts
    -> StringReplacer_2
StringReplacer_2
    CASE = NO
    FIND_TEXT = .*\.
    NO_MATCH = _FME_NO_OP_
    REGEXP = YES
    SRC_ATTRS = _mils
    -> SubstringExtractor
SubstringExtractor
    END = 2
    RESULT_ATTR = _subMils
    SRC_STRING = @Value(_mils)
    START = 0
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)
