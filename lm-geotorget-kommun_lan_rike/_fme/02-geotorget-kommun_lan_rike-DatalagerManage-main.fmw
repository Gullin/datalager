FME workspace 02-geotorget-kommun_lan_rike-DatalagerManage-main.fmw

Parameters:
- RotDirectory = ../   # Katalogen där processen startar
- ProcessName =   # Processnamn
- InData = C:\temp\slask\datalager\lm-geotorget-kommun_lan_rike\_ned\kommun-lan-rike_aktuell.zip   # Indata (shape eller zip)
- InData-DatabaseTable = Skåne_län_Shape_NVDB_DK_O_23_Farjeled Skåne_län_Shape_NVDB_DK_O_2_Vaghallare_domainmap Skåne_län_Shape_NVDB_DK_O_88_Vagtrafiknat Skåne_län_Shape_AGGREGAT_O_67_Vagslag_domainmap Skåne_län_Shape_NVDB_DK_O_2_Vaghallare Skåne_län_Shape_NVDB_DK_O_48_Hastighetsgrans_domainmap Skåne_län_Shape_NVDB_DK_O_4_Vagnummer Skåne_län_Shape_AGGREGAT_O_67_Vagslag Skåne_län_Shape_NVDB_DK_O_88_Vagtrafiknat_domainmap Skåne_län_Shape_NVDB_DK_O_39_RekomVagFarligtGods Skåne_län_Shape_NVDB_DK_O_39_RekomVagFarligtGods_domainmap Skåne_län_Shape_NVDB_DK_O_48_Hastighetsgrans
- OutputDirectory = ../   # Katalog för lagring av del av datalager
- ProcessModulName =   # Processmodulsnamn
- IsWholeProcessRun = 1   # Är hela datalagerprocessen körd
- PG_SCHEMA =   # PostgreSQL Schema
- Manifest = $(RotDirectory)$(ProcessModulName)/_schema/schema-manifest.xlsx   # Manifest (export- och schema-specifikation)
- SchemaFlush = $(RotDirectory)$(ProcessModulName)/_schema/schema-flush.xlsx   # Schemaspecifikation för aktuellt data
- DestDataset_POSTGIS = PG_DATALAGER   # Connection
- DestDataset_POSTGIS_14 = PG_DATALAGER_ADMSRV0118   # Connection

Readers:
- OGCGEOPACKAGE_3: OGCGEOPACKAGE from $(InData)
- XLSXR_2: XLSXR from $(Manifest)

Writers:
- SDF3_2: SDF3 to $(OutputDirectory)
- SHAPEFILE_2: SHAPEFILE to $(OutputDirectory)
- POSTGIS_3: POSTGIS to $(DestDataset_POSTGIS)
- POSTGIS_1: POSTGIS to $(DestDataset_POSTGIS_14)
- OGCGEOPACKAGE_2: OGCGEOPACKAGE to $(OutputDirectory)

rike (reader OGCGEOPACKAGE_3)
    attributes: objektidentitet text, objektversion int, versiongiltigfran datetime, versiongiltigtill datetime, objekttyp text, enhetstyp text, gransstatus text, landskod text, nationellidentifieringskod text, hogstaforvaltningsniva text, beslutatnamn text, namnkortform text, landareal_varde int, landareal_enhet text, vattenareal_varde int, vattenareal_enhet text, totalareal_varde int, totalareal_enhet text, referensdatumfran date, referensdatumtill date, id int,PrimaryKey
    -> ParameterFetcher
Note: Workspace som inte används direkt, utan kallas på genom ett s.k. driver-workspace / Parametrar / Parametrarna sätts i DRIVER-skriptet programmatiskt / * [RotDirectory] Kommer från batch-processen och är obligatoriskt för alla FME-processor. / * [ProcessName] Kommer från batch-processen och är obligatoriskt för alla FME-processor. / * [Manifest] Excel-fil från ett tidigare exporterat schema anpassad med nya kolumnnamn samt vilken data som ska exporteras. Används i detta skript för att bygga upp gällande schema för resp. feature type. / * [OutputDirectory] Katalogsökväg för exporterad geodata (delrepository). / * [ProcessModulName] / * [IsWholeProcesRun]
ParameterFetcher
    ATTR_LIST = ProcessName $(ProcessName) RotDirectory $(RotDirectory)
    -> StringConcatenator
StringConcatenator
    ACTION = Create New Attribute
    PARM_LINE = @Value(ProcessName)_MAIN
    VAL_ATTR = ProcessName_MAIN
    -> UUIDGenerator
UUIDGenerator
    UUID_ATTR = ProcessID
    UUID_FORMAT = UUID_ONLY
    -> Sampler_2
    -> Junction_3
Junction_3
    -> Reprojector_3
    -> Reprojector_4
    -> AttributeCreator_7
Reprojector_3
    DEST = EPSG:3008
    INTERPOLATION_TYPE_NAME = Nearest Neighbor
    RASTER_CELL_SIZE = Preserve Cells
    RASTER_TOLERANCE = 0.0
    SOURCE = EPSG:3006
    REPROJECTED -> AttributeCreator_5
AttributeCreator_5
    ATTR_TABLE = SET_TO refsys = sweref991330
    -> CoordinateSystemSetter
CoordinateSystemSetter
    COORDSYS = EPSG:3008
    -> Junction_4
Reprojector_4
    DEST = EPSG:4326
    INTERPOLATION_TYPE_NAME = Nearest Neighbor
    RASTER_CELL_SIZE = Preserve Cells
    RASTER_TOLERANCE = 0.0
    SOURCE = EPSG:3006
    REPROJECTED -> AttributeCreator_6
AttributeCreator_6
    ATTR_TABLE = SET_TO refsys = wgs84_latlong
    -> CoordinateSystemSetter_2
CoordinateSystemSetter_2
    COORDSYS = EPSG:4326
    -> Junction_4
AttributeCreator_7
    ATTR_TABLE = SET_TO refsys = sweref99tm
    -> CoordinateSystemSetter_3
CoordinateSystemSetter_3
    COORDSYS = EPSG:3006
    -> Junction_4
Junction_4
    -> SchemaMapper
SchemaMapper
    DATASET = $(Manifest)
    FORMAT = XLSXR
    IDXDESTATTR = fme_feature_type
    IDXDESTCOL = dl_new_feature_type_name
    IDXSOURCEATTR = fme_feature_type
    IDXSOURCECOL = fme_feature_type_name
    MAP_ATTRS = column_name dl_new_column_name $(FME_ASC_16)
    ROW_ID_ATTR = _schemamapper_row_ids
    TABLE = schema
    XLSXR_ALLOW_DOLLAR_SIGNS = YES
    XLSXR_APPLY_FILTERS = No
    XLSXR_CASE_SENSITIVE_FEATURE_TYPES = YES
    XLSXR_CONFIGURATION_DATASET = $(Manifest)
    XLSXR_CREATE_FEATURE_TABLES_FROM_DATA = Yes
    XLSXR_EXCEL_COL_NAMES = YES
    XLSXR_EXPAND_MERGED_CELLS = Yes
    XLSXR_FORCE_DATETIME = NO
    XLSXR_QUERY_FEATURE_TYPES_FOR_MERGE_FILTERS = Yes
    XLSXR_READ_BLANK_AS = Missing
    XLSXR_READ_FORM_CONTROLS = NONE
    XLSXR_READ_RASTER_MODE = None
    XLSXR_REPLACE_ONLY_NEWLINES_CARRIAGE_RETURNS = YES
    XLSXR_SCAN_MAX_FEATURES = 1000
    XLSXR_SCHEMA = schema,0,filter_fme_feature_type,char,17,,,1,filter_export_column,char,10,,,2,fme_feature_type_name,char,7,,,3,dl_need_new_feature_type_name,char,6,,,4,dl_new_feature_type_name,char,7,,,5,column_name,char,27,,,6,dl_need_new_column_name,char,6,,,7,dl_new_column_name,char,27,,,8,dl_export,char,6,,,9,fme_data_type,char,21,,,10,native_data_type,char,15,,,11,fme_format_long_name,char,15,,,12,fme_format_short_name,char,14,,,13,_dirpath,char,87,,,14,_extension,char,5,,,15,DatasetFull,char,29,,,16,Dataset,char,24,,,17,column_name_char_length,number,3," 0",,18,feature_type_name_naming_convention,char,12,,,19,column_name_naming_convention,char,12,,,20,test_naming_convention,char,47,,,1,,,,NO,NO,1,C:\temp\slask\datalager\lm-geotorget-kommun_lan_rike\_schema\schema-manifest.xlsx,"0,0,20,65",,NO,NO
    XLSXR_SCHEMA_HANDLING_REVISION = 2
    XLSXR_SKIP_EMPTY_ROWS = YES
    XLSXR_STRIP_SHEETNAME_SPACES = YES
    XLSXR_TABLELIST = schema
    XLSXR_TRIM_ATTR_NAME_WHITESPACE = Yes
    XLSXR_USE_CUSTOM_SCHEMA = NO
    MAPPED -> FeatureMerger [REQUESTOR]
    UNMAPPED -> Aggregator_6
schema (reader XLSXR_2)
    attributes: filter_fme_feature_type char(17), filter_export_column char(10), fme_feature_type_name char(7), dl_need_new_feature_type_name char(6), dl_new_feature_type_name char(7), column_name char(27), dl_need_new_column_name char(6), dl_new_column_name char(27), dl_export char(6), fme_data_type char(21), native_data_type char(15), fme_format_long_name char(15), fme_format_short_name char(14), _dirpath char(87), _extension char(5), DatasetFull char(29), Dataset char(24), column_name_char_length number(3,0), feature_type_name_naming_convention char(12), column_name_naming_convention char(12), test_naming_convention char(47)
    -> Tester
Tester
    BOOL_OP = OR
    TEST_CLAUSE = TEST @Value(dl_export) = true
    TEST_MODE = TEST
    PASSED -> AttributeManager
AttributeManager
    ATTR_TABLE:
      REMOVE filter_fme_feature_type
      REMOVE filter_export_column
      REMOVE column_name
      REMOVE dl_need_new_column_name
      RENAME_SET_VALUE dl_new_column_name > name
      REMOVE dl_export
      REMOVE _dirpath
      REMOVE _extension
      REMOVE DatasetFull
      REMOVE Dataset
      REMOVE column_name_char_length
    -> Aggregator_2
Aggregator_2
    ACCUM_ATTRS_NAME = Use Attributes From One Feature
    AGGREGATE_TYPE = Homogeneous Collection (If Possible)
    COUNT_ATTR = Antal
    GROUP_BY = fme_feature_type fme_feature_type_name fme_format_long_name fme_format_short_name dl_new_feature_type_name
    LIST_ATTRS_TO_INCLUDE = fme_data_type name native_data_type
    LIST_NAME = attribute
    MODE = Geometry - Assemble One Level
    SEP = ,
    AGGREGATE -> AttributeKeeper_2
AttributeKeeper_2
    CREATE_BULK_MODE_FEATURES = NO
    KEEP_ATTRS = fme_feature_type_name,fme_format_long_name,fme_format_short_name,dl_new_feature_type_name
    KEEP_LIST = attribute{}
    -> FeatureMerger [SUPPLIER]
FeatureMerger
    ATTR_ACCUM_MODE = Merge Supplier
    ATTR_CONFLICT_RES = Use Requestor
    IGNORE_NULLS = No
    JOIN_KEYS = @Value(fme_feature_type) @Value(dl_new_feature_type_name) AUTO
    MERGE_TYPE = Attributes Only
    PROCESS_DUPS = NO
    REJECT_NULL_MISSING_KEYS = No
    SUPPLIERS_FIRST = No
    MERGED -> AttributeCreator
    UNMERGED_REQUESTOR -> Aggregator_8
AttributeCreator
    ATTR_TABLE = SET_TO _name_extension
    -> ArcStroker
Note: ArcStroker [ArcStroker Version 5] / General: / Stroke By: Maximum Deviation / Maximum Deviation: 0.02 / Make Polygon Out of 360 Degree Arcs: No
ArcStroker
    MAKE_POLY = No
    STROKE_CHOICE = Maximum Deviation
    TOLERANCE_VAL = 0.02
    STROKED -> 2DForcer
2DForcer
    2D -> GeometryRefiner
GeometryRefiner
    -> GeometryFilter
GeometryFilter
    FILTER_MODE = COMPLETE
    FILTER_MULTI = FILTER_TYPES]"Curve MultiCurve Area MultiArea Point MultiPoint Arc Ellipse Text MultiText Raster PointCloud Surface MultiSurface Solid MultiSolid Aggregate Null GeometryInstance Donut SimpleArea Polygon Path Segment Line OrientedArc"]INSTANCES]INSTANCE]FME_CONTROLLER_QUERY_FILE]]FME_CONTROLLER_CHOICE]Complete
    Null -> Junction_5
    Point -> Junction_5
    MultiPoint -> Junction_5
    Text -> Junction_5
    MultiText -> Junction_5
    Curve -> Junction_5
    Segment -> Junction_5
    Line -> Junction_5
    Arc -> Junction_5
    OrientedArc -> Junction_5
    Path -> Junction_5
    MultiCurve -> Junction_5
    Area -> StringConcatenator_6
    SimpleArea -> StringConcatenator_6
    Polygon -> StringConcatenator_6
    Ellipse -> StringConcatenator_32
    Donut -> StringConcatenator_6
    MultiArea -> StringConcatenator_6
    Surface -> Junction_5
    MultiSurface -> Junction_5
    Solid -> Junction_5
    MultiSolid -> Junction_5
    Raster -> Junction_5
    PointCloud -> Junction_5
    Aggregate -> Junction_5
    GeometryInstance -> Junction_5
    <UNFILTERED> -> Junction_5
StringConcatenator_6
    ACTION = Create New Attribute
    PARM_LINE = fme_basicstring:32%23%3:@Value(dl_new_feature_type_name)@Value(_name_extension)_my
    VAL_ATTR = DatasetName
    -> StringCaseChanger_4
StringConcatenator_32
    ACTION = Create New Attribute
    PARM_LINE = fme_basicstring:32%23%3:@Value(dl_new_feature_type_name)@Value(_name_extension)_my
    VAL_ATTR = DatasetName
    -> StringCaseChanger_6
Junction
    -> NullAttributeMapper
    -> Junction_2
    -> StringConcatenator_10
    -> CreateLocalGeopackageKey
NullAttributeMapper
    ATTRCHOICE = All Attributes
    NULL_TREATMENT = Null
    SOURCE_ATTR_VAL = Null
    -> AttributeExposer_2
AttributeExposer_2
    ATTR_LIST = fme_type
    -> AttributeCreator_2
AttributeCreator_2
    ATTR_TABLE = SET_TO fme_geometry{0} = @Value(fme_type)
    -> Shapefile1 (writer SHAPEFILE_2)
Shapefile1 (writer SHAPEFILE_2)
StringConcatenator_10
    ACTION = Overwrite Existing Attributes
    ATTRLIST = DatasetName
    PARM_LINE = fme_basicstring:14%1%19:@Value(refsys)_@Value(DatasetName)
    -> schema (writer POSTGIS_3)
    -> Table1 (writer POSTGIS_1)
Junction_5
    -> Aggregator
Creator
    GEOMTYPE = Geometry Object
    NUM = 1
    CREATED -> ParameterFetcher_2
ParameterFetcher_2
    ATTR_LIST = ProcessName $(ProcessName) RotDirectory $(RotDirectory)
    -> StringConcatenator_8
StringConcatenator_8
    ACTION = Create New Attribute
    PARM_LINE = @Value(ProcessName)_MAIN
    VAL_ATTR = ProcessName_MAIN
    -> UUIDGenerator_2
UUIDGenerator_2
    UUID_ATTR = ProcessID
    UUID_FORMAT = UUID_ONLY
    -> AttributeCreator_12_OUTPUT
AttributeCreator_12_OUTPUT: Junction
    -> FeatureMerger_2 [SUPPLIER]
    -> FeatureMerger_3 [SUPPLIER]
    -> FeatureMerger_4 [SUPPLIER]
    -> FeatureMerger_6 [SUPPLIER]
    -> FeatureMerger_7 [SUPPLIER]

Bookmark: Loggning
Aggregator_6
    ACCUM_ATTRS_NAME = Use Attributes From One Feature
    AGGREGATE_TYPE = Homogeneous Collection (If Possible)
    GROUP_BY = fme_feature_type
    MODE = Geometry - Assemble One Level
    SEP = ", "
    AGGREGATE -> Aggregator_7
Aggregator_7
    ACCUM_ATTRS_NAME = Use Attributes From One Feature
    AGGREGATE_TYPE = Homogeneous Collection (If Possible)
    CONCAT_ATTRS = fme_feature_type
    MODE = Geometry - Assemble One Level
    SEP = ", "
    AGGREGATE -> FeatureMerger_6 [REQUESTOR]
Note: Endast till för som signal att starta logg
Sampler_2
    RATE = 1
    SAMPLE_MODE = No
    SAMPLE_TYPE_LONG = First N Features
    SAMPLED -> FeatureMerger_2 [REQUESTOR]
Junction_2
    -> Aggregator_4
Aggregator_4
    ACCUM_ATTRS_NAME = Use Attributes From One Feature
    AGGREGATE_TYPE = Homogeneous Collection (If Possible)
    COUNT_ATTR = Antal
    MODE = Geometry - Assemble One Level
    SEP = ", "
    AGGREGATE -> FeatureMerger_4 [REQUESTOR]
Aggregator
    ACCUM_ATTRS_NAME = Use Attributes From One Feature
    AGGREGATE_TYPE = Homogeneous Collection (If Possible)
    GROUP_BY = fme_feature_type
    MODE = Geometry - Assemble One Level
    SEP = ,
    AGGREGATE -> Aggregator_3
Aggregator_3
    ACCUM_ATTRS_NAME = Use Attributes From One Feature
    AGGREGATE_TYPE = Homogeneous Collection (If Possible)
    CONCAT_ATTRS = fme_feature_type
    COUNT_ATTR = Antal
    MODE = Geometry - Assemble One Level
    SEP = ", "
    AGGREGATE -> FeatureMerger_3 [REQUESTOR]
Aggregator_8
    ACCUM_ATTRS_NAME = Use Attributes From One Feature
    AGGREGATE_TYPE = Homogeneous Collection (If Possible)
    GROUP_BY = fme_feature_type
    MODE = Geometry - Assemble One Level
    SEP = ", "
    AGGREGATE -> Aggregator_9
Aggregator_9
    ACCUM_ATTRS_NAME = Use Attributes From One Feature
    AGGREGATE_TYPE = Homogeneous Collection (If Possible)
    CONCAT_ATTRS = fme_feature_type
    MODE = Geometry - Assemble One Level
    SEP = ", "
    AGGREGATE -> FeatureMerger_7 [REQUESTOR]
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_2
StringConcatenator_2
    ACTION = Create New Attribute
    PARM_LINE = Kör @Value(ProcessName_MAIN) för data i "$(Manifest)" till datalagret.
    VAL_ATTR = Logg
    -> DTStamperYYYY-MM-DD_HH:MI:SS.sss
DTStamperYYYY-MM-DD_HH:MI:SS.sss
    -> Logg_2
Logg_2: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,INFORMATION,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_6
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_11
StringConcatenator_11
    ACTION = Create New Attribute
    PARM_LINE = fme_basicstring:37%24%31:Kolumner och dess namn i dataset(en) @Value(fme_feature_type) har ej länkats till nytt namn.
    VAL_ATTR = Logg
    -> DTStamperYYYY-MM-DD_HH:MI:SS.sss_5
DTStamperYYYY-MM-DD_HH:MI:SS.sss_5
    -> Logg_6
Logg_6: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_7
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_12
StringConcatenator_12
    ACTION = Create New Attribute
    PARM_LINE = fme_basicstring:12%24%180:Dataset(en) @Value(fme_feature_type) har ej länkats till något schema. Kommer ej att kunna skapas med attribut. Kontrollera anledningen till att dataset åkt igenom utan upptagning på korrekt sätt i schemahanteringen.
    VAL_ATTR = Logg
    -> DTStamperYYYY-MM-DD_HH:MI:SS.sss_6
DTStamperYYYY-MM-DD_HH:MI:SS.sss_6
    -> Logg_7
Logg_7: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_9
StringConcatenator_9
    ACTION = Create New Attribute
    PARM_LINE = @Value(ProcessName_MAIN) avslutad med @Value(Antal) st. objekt skrivna till datalagret.
    VAL_ATTR = Logg
    -> DTStamperYYYY-MM-DD_HH:MI:SS.sss_4
DTStamperYYYY-MM-DD_HH:MI:SS.sss_4
    -> Logg_4
Logg_4: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,KLART,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_3
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_3
StringConcatenator_3
    ACTION = Create New Attribute
    PARM_LINE = Geometrier från objektklasser (@Value(fme_feature_type)) skrivs ej till shape-filer.
    VAL_ATTR = Logg
    -> DTStamperYYYY-MM-DD_HH:MI:SS.sss_3
DTStamperYYYY-MM-DD_HH:MI:SS.sss_3
    -> Logg_3
Logg_3: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)

Bookmark: FDO_Area
StringCaseChanger_4
    ATTRCHOICE = Selected Attributes
    ATTRLIST = DatasetName
    CHANGE_TYPE = lowercase
    -> FeatureClass10002 (writer SDF3_2)
    -> Junction_2
    -> Junction
Note: : lkr_gis [SDF3] Area
FeatureClass10002 (writer SDF3_2)

Bookmark: FDO_Ellipse
StringCaseChanger_6
    ATTRCHOICE = Selected Attributes
    ATTRLIST = DatasetName
    CHANGE_TYPE = lowercase
    -> FeatureClass10003 (writer SDF3_2)
    -> Junction_2
    -> Junction
Note: : lkr_gis [SDF3] Ellipse
FeatureClass10003 (writer SDF3_2)

Bookmark: PostGIS
Note: BUGG (FME 2021.0): / "Table Qualifier" i writer fungerar inte med dynamisk skrivning. Värdet behöver konkatineras i "Table Name"
schema (writer POSTGIS_3)
Table1 (writer POSTGIS_1)

Bookmark: GeoPackage
CreateLocalGeopackageKey
    DATASETNAME = @Value(DatasetName)
    LIST_NAME = attribute{}
    -> AttributeExposer_4
AttributeExposer_4
    ATTR_LIST = fme_type
    -> AttributeCreator_45
AttributeCreator_45
    ATTR_TABLE = SET_TO fme_geometry{0} = @Value(fme_type)
    -> Table1 (writer OGCGEOPACKAGE_2)
Table1 (writer OGCGEOPACKAGE_2)

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    INCLUDE_OFFSET = NO
    STAMP_TYPE = datetime
    TIMEZONE = local
    -> DateTimeConverter
DateTimeConverter
    DATETIME_ATTR = _dts
    OUT_FORMAT = %Y-%m-%d %H:%M:%S
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    NO_MATCH = _FME_NO_OP_
    REGEXP = YES
    SRC_ATTRS = _dts
    -> StringReplacer_2
StringReplacer_2
    CASE = NO
    FIND_TEXT = .*\.
    NO_MATCH = _FME_NO_OP_
    REGEXP = YES
    SRC_ATTRS = _mils
    -> SubstringExtractor
SubstringExtractor
    END = 2
    RESULT_ATTR = _subMils
    SRC_STRING = @Value(_mils)
    START = 0
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)

FME custom transformer CreateLocalGeopackageKey

Parameters:
- DATASETNAME = @Value(DatasetName)   # DatasetName
- LIST_NAME = attribute{}   # "" List Attribute

Input (input)
    -> Counter
Output (output)

Bookmark: Skapa godtycklig primärnyckel åt GeoPackage
Counter
    CNT_ATTR = gpkg_id
    GROUP_BY = DatasetName
    SCOPE = Local
    START = 1
    -> AttributeCreator_4
AttributeCreator_4
    ATTR_TABLE:
      SET_TO name = gpkg_id
      SET_TO fme_data_type = fme_int64,PrimaryKey
    -> ListElementCounter
ListElementCounter
    CNT_ATTR = _attribute_element_count
    LIST_NAME = $(LIST_NAME)
    -> AttributeCreator_5
AttributeCreator_5
    ATTR_TABLE:
      SET_TO attribute{@Value(_attribute_element_count)}.name = @Value(name)
      SET_TO attribute{@Value(_attribute_element_count)}.fme_data_type = @Value(fme_data_type)
    -> AttributeRemover
AttributeRemover
    REMOVE_ATTRS = fme_data_type,name
    -> Output (output)
