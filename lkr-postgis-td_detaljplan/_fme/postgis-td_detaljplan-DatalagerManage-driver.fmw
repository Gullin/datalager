FME workspace postgis-td_detaljplan-DatalagerManage-driver.fmw

Parameters:
- FME_USER_PARAM_PRIVATE_GRP =
- IsWholeProcessRun =
- OutputDirectory =
- PG_SCHEMA =
- ProcessModulName =
- ProcessName =
- RotDirectory =
- SchemaFlush =

Readers:
- XLSXR_1: XLSXR from $(SchemaFlush)

Creator
    GEOMTYPE = Geometry Object
    NUM = 1
    CREATED -> ParameterFetcher_2
ParameterFetcher_2
    ATTR_LIST = ProcessName $(ProcessName) RotDirectory $(RotDirectory)
    -> StringConcatenator_8
StringConcatenator_8
    ACTION = Create New Attribute
    PARM_LINE = @Value(ProcessName)_DRIVER
    VAL_ATTR = ProcessName_DRIVER
    -> UUIDGenerator_2
UUIDGenerator_2
    UUID_ATTR = ProcessID
    -> AttributeCreator_12
AttributeCreator_12
    ATTR_TABLE = SET_TO _FeatureIdMerger = 1
    -> AttributeCreator_12_OUTPUT_-__FeatureMerger_3_SUPPLIER
AttributeCreator_12_OUTPUT_-__FeatureMerger_3_SUPPLIER: Junction
    -> Junction
    -> Junction_3
    -> Junction_5
    -> Junction_7
    -> Junction_9
Note: FeatureMerger_2 : Supplier
Junction
    -> Junction_2
Note: FeatureMerger_3 : Supplier
Junction_3
    -> Junction_4
Note: FeatureMerger_4 : Supplier
Junction_5
    -> Junction_6
Note: FeatureMerger_5 : Supplier
Junction_7
    -> Junction_8
Note: FeatureMerger_6 : Supplier
Junction_9
    -> Junction_10
Note: Parametrar / * [RotDirectory] Kommer från batch-processen och är obligatoriskt för alla FME-processor. / * [ProcessName] Kommer från batch-processen och är obligatoriskt för alla FME-processor. / * [Manifest] Excel-fil från ett tidigare exporterat schema anpassad med nya kolumnnamn samt vilken data som ska exporteras. / * [OutputDirectory] Katalogsökväg för exporterad geodata (delrepository).
schema (reader XLSXR_1)
    attributes: fme_feature_type_name char(20), column_name char(16), dl_need_new_column_name char(6), dl_new_column_name char(12), dl_export char(5), fme_data_type char(18), native_data_type char(14), fme_format_long_name char(22), fme_format_short_name char(15), _dirpath char(1), _extension char(1), DatasetFull char(8), Dataset char(8), column_name_char_length number(3,0)
    -> Tester_4
Tester_4
    BOOL_OP = OR
    TEST_CLAUSE = TEST @Value(dl_export) = true
    TEST_MODE = TEST
    PASSED -> Tester_2
    PASSED -> Aggregator_3
    PASSED -> Sampler_2
Aggregator_3
    ACCUM_ATTRS_NAME = Drop Incoming Attributes
    AGGREGATE_TYPE = Homogeneous Collection (If Possible)
    GROUP_BY = fme_feature_type_name fme_format_short_name Dataset
    MODE = Geometry - Assemble One Level
    ORDERED = No
    SEP = ,
    AGGREGATE -> TestFilter
Note: Format som stöds
TestFilter
    DEFAULT_VALUE = <UNFILTERED>
    TEST_LIST = "BOOL_OP,OR,COMPOSITE_TEST,""""""<Unused>"""""",TEST_CLAUSE,TEST @Value(fme_format_short_name) = POSTGIS",POSTGIS
    POSTGIS -> WorkspaceRunner
    <UNFILTERED> -> Aggregator
WorkspaceRunner
    BLOCKING = Yes
    WORKSPACE_FILE = $(FME_MF_DIR)postgis-td_detaljplan-DatalagerManage-main-POSTGIS.fmw
    WORKSPACE_PARAMETERS = RotDirectory,$(RotDirectory),ProcessName,$(ProcessName),OutputDirectory,$(OutputDirectory),ProcessModulName,$(ProcessModulName),IsWholeProcessRun,$(IsWholeProcessRun),SchemaFlush,$(SchemaFlush),DatabaseSchema,@Value(Dataset),PG_SCHEMA,$(PG_SCHEMA),DestDataset_POSTGIS,PG_DATALAGER,DestDataset_POSTGIS_14,PG_DATALAGER_ADMSRV0118,Datatable,@Value(fme_feature_type_name)
    SUCCEEDED -> AttributeCreator_2
    FAILED -> StringConcatenator_3
    SUMMARY -> AttributeCreator_3

Bookmark: Loggning
Note: AttributeCreator_12_-_FeatureMerger_3
Junction_2
    -> FeatureMerger_2 [SUPPLIER]
Note: AttributeCreator_12_-_FeatureMerger_3
Junction_4
    -> FeatureMerger_3 [SUPPLIER]
Note: AttributeCreator_12_-_FeatureMerger_3
Junction_6
    -> FeatureMerger_4 [SUPPLIER]
Note: AttributeCreator_12_-_FeatureMerger_3
Junction_8
    -> FeatureMerger_5 [SUPPLIER]
Note: AttributeCreator_12_-_FeatureMerger_3
Junction_10
    -> FeatureMerger_6 [SUPPLIER]
StringConcatenator_3
    ACTION = Create New Attribute
    PARM_LINE = @Value(Dataset).@Value(fme_feature_type_name) (@Value(fme_format_short_name))
    VAL_ATTR = _result
    -> AttributeCreator_6
AttributeCreator_6
    ATTR_TABLE = SET_TO _FeatureIdMerger = 1
    -> FeatureMerger_5 [REQUESTOR]
FeatureMerger_5
    ATTR_ACCUM_MODE = Merge Supplier
    ATTR_CONFLICT_RES = Use Requestor
    CLEANING_TOLERANCE = None
    IGNORE_NULLS = No
    JOIN_KEYS = @Value(_FeatureIdMerger) @Value(_FeatureIdMerger) AUTO
    MERGE_TYPE = Attributes Only
    PROCESS_DUPS = No
    REJECT_NULL_MISSING_KEYS = No
    SUPPLIERS_FIRST = No
    MERGED -> StringConcatenator_7
StringConcatenator_7
    ACTION = Create New Attribute
    PARM_LINE = @Value(_result) - kunde inte exporteras. Fel: @Value(_failure_message)
    VAL_ATTR = Logg
    -> DTStamperYYYY-MM-DD_HH:MI:SS.sss_4
DTStamperYYYY-MM-DD_HH:MI:SS.sss_4
    -> Logg_6
Logg_6: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Sampler_5
    RATE = 1
    SAMPLE_MODE = No
    SAMPLE_TYPE_LONG = First N Features
    SAMPLED -> AttributeCreator_7
StringConcatenator_5
    ACTION = Create New Attribute
    PARM_LINE = Kör @Value(ProcessName_DRIVER) för data definierad i "" till datalagret.
    VAL_ATTR = Logg
    -> DTStamperYYYY-MM-DD_HH:MI:SS.sss_5
DTStamperYYYY-MM-DD_HH:MI:SS.sss_5
    -> Logg_5
Logg_5: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,KLART,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: Format som det ej finns stöd för men som är / definierade som exporterbara i manifest
Aggregator
    ACCUM_ATTRS_NAME = Use Attributes From One Feature
    AGGREGATE_TYPE = Homogeneous Collection (If Possible)
    COUNT_ATTR = Antal
    GROUP_BY = fme_format_short_name
    MODE = Geometry - Assemble One Level
    ORDERED = No
    SEP = ", "
    AGGREGATE -> AttributeCreator_5
AttributeCreator_5
    ATTR_TABLE = SET_TO _FeatureIdMerger = 1
    -> FeatureMerger_4 [REQUESTOR]
FeatureMerger_4
    ATTR_ACCUM_MODE = Merge Supplier
    ATTR_CONFLICT_RES = Use Requestor
    CLEANING_TOLERANCE = None
    IGNORE_NULLS = No
    JOIN_KEYS = @Value(_FeatureIdMerger) @Value(_FeatureIdMerger) AUTO
    MERGE_TYPE = Attributes Only
    PROCESS_DUPS = No
    REJECT_NULL_MISSING_KEYS = No
    SUPPLIERS_FIRST = No
    MERGED -> StringConcatenator_4
StringConcatenator_4
    ACTION = Create New Attribute
    PARM_LINE = Följande @Value(Antal)  st. format stöds ej (@Value(fme_format_short_name)). För att export ska vara fullt möjligt enligt manifest, ändra i manifest eller definiera ny WorkspaceRunner med workspace.
    VAL_ATTR = Logg
    -> DTStamperYYYY-MM-DD_HH:MI:SS.sss_3
DTStamperYYYY-MM-DD_HH:MI:SS.sss_3
    -> Logg_4
Logg_4: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: Följande kolumn förekommer fler än / en gång för specifikt dataset
Aggregator_4
    ACCUM_ATTRS_NAME = Use Attributes From One Feature
    AGGREGATE_TYPE = Homogeneous Collection (If Possible)
    COUNT_ATTR = Antal
    GROUP_BY = dl_new_column_name
    MODE = Geometry - Assemble One Level
    ORDERED = No
    SEP = ", "
    AGGREGATE -> AttributeCreator_4
AttributeCreator_4
    ATTR_TABLE = SET_TO _FeatureIdMerger = 1
    -> FeatureMerger_3 [REQUESTOR]
FeatureMerger_3
    ATTR_ACCUM_MODE = Merge Supplier
    ATTR_CONFLICT_RES = Use Requestor
    CLEANING_TOLERANCE = None
    IGNORE_NULLS = No
    JOIN_KEYS = @Value(_FeatureIdMerger) @Value(_FeatureIdMerger) AUTO
    MERGE_TYPE = Attributes Only
    PROCESS_DUPS = No
    REJECT_NULL_MISSING_KEYS = No
    SUPPLIERS_FIRST = No
    MERGED -> StringConcatenator_6
StringConcatenator_6
    ACTION = Create New Attribute
    PARM_LINE = Följande @Value(Antal)  st. kolumner finns det dubbletter för (@Value(dl_new_column_name)). För att exporterad data vara läsbar enligt manifest, ändra kolumnnamn i manifest.
    VAL_ATTR = Logg
    -> DTStamperYYYY-MM-DD_HH:MI:SS.sss_2
DTStamperYYYY-MM-DD_HH:MI:SS.sss_2
    -> Logg_3
Logg_3: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: Endast till för som signal att starta logg
Sampler_2
    RATE = 1
    SAMPLE_MODE = No
    SAMPLE_TYPE_LONG = First N Features
    SAMPLED -> AttributeCreator_13
AttributeCreator_13
    ATTR_TABLE = SET_TO _FeatureIdMerger = 1
    -> FeatureMerger_2 [REQUESTOR]
FeatureMerger_2
    ATTR_ACCUM_MODE = Merge Supplier
    ATTR_CONFLICT_RES = Use Requestor
    CLEANING_TOLERANCE = None
    IGNORE_NULLS = No
    JOIN_KEYS = @Value(_FeatureIdMerger) @Value(_FeatureIdMerger) AUTO
    MERGE_TYPE = Attributes Only
    PROCESS_DUPS = No
    REJECT_NULL_MISSING_KEYS = No
    SUPPLIERS_FIRST = No
    MERGED -> StringConcatenator_2
StringConcatenator_2
    ACTION = Create New Attribute
    PARM_LINE = Kör @Value(ProcessName_DRIVER) för data definierad i "" till datalagret.
    VAL_ATTR = Logg
    -> DTStamperYYYY-MM-DD_HH:MI:SS.sss
DTStamperYYYY-MM-DD_HH:MI:SS.sss
    -> Logg_2
Logg_2: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_DRIVER),EX_ID,@Value(ProcessID),EX_TYPE,INFORMATION,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)

Bookmark: Sammanställning Succeeded och Summary
AttributeCreator_2
    ATTR_TABLE = SET_TO FeatureWR-ID = 1
    -> Aggregator_5
Aggregator_5
    ACCUM_ATTRS_NAME = Use Attributes From One Feature
    AGGREGATE_TYPE = Homogeneous Collection (If Possible)
    COUNT_ATTR = AntalSuccess
    MODE = Geometry - Assemble One Level
    ORDERED = No
    SEP = ,
    AGGREGATE -> FeatureMerger [REQUESTOR]
AttributeCreator_3
    ATTR_TABLE = SET_TO FeatureWR-ID = 1
    -> FeatureMerger [SUPPLIER]
FeatureMerger
    ATTR_ACCUM_MODE = Merge Supplier
    ATTR_CONFLICT_RES = Use Requestor
    CLEANING_TOLERANCE = None
    IGNORE_NULLS = No
    JOIN_KEYS = @Value(FeatureWR-ID) @Value(FeatureWR-ID) AUTO
    MERGE_TYPE = Attributes Only
    PROCESS_DUPS = No
    REJECT_NULL_MISSING_KEYS = No
    SUPPLIERS_FIRST = No
    MERGED -> Sampler_5

Bookmark: För loggning
AttributeCreator_7
    ATTR_TABLE = SET_TO _FeatureIdMerger = 1
    -> FeatureMerger_6 [REQUESTOR]
FeatureMerger_6
    ATTR_ACCUM_MODE = Merge Supplier
    ATTR_CONFLICT_RES = Use Requestor
    CLEANING_TOLERANCE = None
    IGNORE_NULLS = No
    JOIN_KEYS = @Value(_FeatureIdMerger) @Value(_FeatureIdMerger) AUTO
    MERGE_TYPE = Attributes Only
    PROCESS_DUPS = No
    REJECT_NULL_MISSING_KEYS = No
    SUPPLIERS_FIRST = No
    MERGED -> StringConcatenator_5

Bookmark: Kontrollera om kolumnnamn förekommer fler än en gång per dataset
Tester_2
    BOOL_OP = AND
    TEST_CLAUSE:
      TEST @Value(dl_need_new_column_name) = true
      TEST @Value(dl_new_column_name) ATTRIBUTE_HAS_VALUE ""
    TEST_MODE = TEST
    PASSED -> AttributeCreator
AttributeCreator
    ATTR_TABLE = SET_TO column_name = @Value(dl_new_column_name)
    -> Aggregator_2
Aggregator_2
    ACCUM_ATTRS_NAME = Use Attributes From One Feature
    AGGREGATE_TYPE = Homogeneous Collection (If Possible)
    COUNT_ATTR = AntalSameColumns
    GROUP_BY = fme_feature_type_name dl_new_column_name
    MODE = Geometry - Assemble One Level
    ORDERED = No
    SEP = ,
    AGGREGATE -> Tester_3
Tester_3
    BOOL_OP = OR
    TEST_CLAUSE = TEST @Value(AntalSameColumns) > 1
    TEST_MODE = TEST
    PASSED -> Aggregator_4

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    INCLUDE_OFFSET = NO
    STAMP_TYPE = datetime
    TIMEZONE = local
    -> DateTimeConverter
DateTimeConverter
    DATETIME_ATTR = _dts
    OUT_FORMAT = %Y-%m-%d %H:%M:%S
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    NO_MATCH = _FME_NO_OP_
    REGEXP = YES
    SRC_ATTRS = _dts
    -> StringReplacer_2
StringReplacer_2
    CASE = NO
    FIND_TEXT = .*\.
    NO_MATCH = _FME_NO_OP_
    REGEXP = YES
    SRC_ATTRS = _mils
    -> SubstringExtractor
SubstringExtractor
    END = 2
    RESULT_ATTR = _subMils
    SRC_STRING = @Value(_mils)
    START = 0
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)
