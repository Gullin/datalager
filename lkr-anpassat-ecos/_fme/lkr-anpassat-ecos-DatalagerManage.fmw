FME workspace lkr-anpassat-ecos-DatalagerManage.fmw

Parameters:
- DestDataset_POSTGIS =
- FME_USER_PARAM_PRIVATE_GRP =
- IsWholeProcessRun =
- Manifest =
- OutSchemaFileExtention =
- OutSchemaFileName =
- OutSchemaFileNameSuffix =
- OutputDirectory =
- PG_SCHEMA =
- PlandokumentDir =
- PlandokumentDir2Nd =
- PlandokumentFileFilter =
- ProcessModulName =
- ProcessName =
- RotDirectory =
- SchemaFlush =

Readers:
- XLSXR_1: XLSXR from $(SchemaFlush)
- SCHEMA_FROM_TABLE_1: SCHEMA_FROM_TABLE from $(Manifest)

Writers:
- SDF3_1: SDF3 to $(OutputDirectory) in EPSG:3008
- SHAPEFILE_1: SHAPEFILE to $(OutputDirectory) in EPSG:3008
- POSTGIS_1: POSTGIS to $(DestDataset_POSTGIS) in EPSG:3008
- POSTGIS_2: POSTGIS to $(DestDataset_POSTGIS) in EPSG:3008

Creator
    GEOMTYPE = Geometry Object
    NUM = 1
    CREATED -> ParameterFetcher_2
ParameterFetcher_2
    ATTR_LIST = ProcessName $(ProcessName) RotDirectory $(RotDirectory)
    -> UUIDGenerator_2
UUIDGenerator_2
    UUID_ATTR = ProcessID
    -> AttributeCreator_12
AttributeCreator_12
    ATTR_TABLE = SET_TO _FeatureIdMerger = 1
    -> AttributeCreator_12_OUTPUT_-__FeatureMerger_3_SUPPLIER
AttributeCreator_12_OUTPUT_-__FeatureMerger_3_SUPPLIER: Junction
    -> Junction
    -> Junction_3
    -> Junction_7
    -> Junction_9
    -> Junction_13
Note: FeatureMerger_2 : Supplier
Junction
    -> Junction_2
Note: FeatureMerger_3 : Supplier
Junction_3
    -> Junction_4
Note: Junction_12 : Input
Junction_13
Note: FeatureMerger_5 : Supplier
Junction_7
Note: FeatureMerger_6 : Supplier
Junction_9
    -> Junction_10
Note: Parametrar / * [RotDirectory] Kommer från batch-processen och är obligatoriskt för alla FME-processor. / * [ProcessName] Kommer från batch-processen och är obligatoriskt för alla FME-processor. / * [Manifest] Excel-fil från ett tidigare exporterat schema anpassad med nya kolumnnamn samt vilken data som ska exporteras. / * [OutputDirectory] Katalogsökväg för exporterad geodata (delrepository).
schema (reader XLSXR_1)
    attributes: fme_feature_type_name char(20), column_name char(16), dl_need_new_column_name char(6), dl_new_column_name char(12), dl_export char(5), fme_data_type char(18), native_data_type char(14), fme_format_long_name char(22), fme_format_short_name char(15), _dirpath char(1), _extension char(1), DatasetFull char(8), Dataset char(8), column_name_char_length number(3,0)
    -> Tester_4
Tester_4
    BOOL_OP = OR
    COMPOSITE_TEST = 1
    TEST_CLAUSE = TEST @Value(dl_export) = true
    TEST_MODE = TEST
    PASSED -> Tester_2
    PASSED -> Aggregator_3
    PASSED -> Sampler_2
Aggregator_3
    ACCUM_ATTRS_NAME = Drop Incoming Attributes
    AGGREGATE_TYPE = Homogeneous Collection (If Possible)
    GROUP_BY = fme_feature_type_name fme_format_short_name Dataset
    MODE = Geometry - Assemble One Level
    SEP = ,
    AGGREGATE -> StringConcatenator
StringConcatenator
    ACTION = Create New Attribute
    PARM_LINE = @Value(Dataset).@Value(fme_feature_type_name)
    VAL_ATTR = _filterValue
    -> StringCaseChanger
StringCaseChanger
    ATTRCHOICE = Selected Attributes
    ATTRLIST = _filterValue
    CHANGE_TYPE = lowercase
    -> TestFilter_2
TestFilter_2
    DEFAULT_VALUE = <UNFILTERED>
    TEST_LIST = "BOOL_OP,OR,COMPOSITE_TEST,""""""1"""""",TEST_CLAUSE,TEST @Value(_filterValue) = fblasa.dbo.byg_regbyg",fblasa.dbo.byg_regbyg,"BOOL_OP,OR,COMPOSITE_TEST,""""""<Unused>"""""",TEST_CLAUSE,TEST @Value(_filterValue) = pg_geodata.td_bal.bal_byggnad_y",pg_geodata.td_bal.bal_byggnad_y,"BOOL_OP,OR,COMPOSITE_TEST,""""""<Unused>"""""",TEST_CLAUSE,TEST @Value(_filterValue) = pg_geodata.td_drk.rk_fastighet_y",pg_geodata.td_drk.rk_fastighet_y
    fblasa.dbo.byg_regbyg -> FeatureReader_2 [INITIATOR]
    pg_geodata.td_bal.bal_byggnad_y -> FeatureReader_3 [INITIATOR]
    pg_geodata.td_drk.rk_fastighet_y -> FeatureReader_4 [INITIATOR]
FeatureReader_2
    ATTR_ACCUM_MODE = Only Use Result
    COMBINE_GEOM = Use Result
    DATASET = @Value(Dataset)
    FEATURETYPES = @Value(fme_feature_type_name)
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = @Value(Dataset)
    MSSQL_ADO_QUERY_FEATURE_TYPES_FOR_MERGE_FILTERS = Yes
    MSSQL_ADO_READ_CACHE_SIZE = 10
    OUTPUT_FEATURES_DISPLAY = Schema and Data Features
    <OTHER> -> ArcStrokerRefiner2D
ArcStrokerRefiner2D
    -> AttributeExposer
AttributeExposer
    ATTR_LIST = kom_bid,UUID
    -> FeatureMerger_7 [SUPPLIER]
FeatureReader_3
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> ArcStrokerRefiner2D_2
ArcStrokerRefiner2D_2
    -> AttributeExposer_2
AttributeExposer_2
    ATTR_LIST = bal_objektidentitet
    -> FeatureMerger_7 [REQUESTOR]
FeatureMerger_7
    ATTR_ACCUM_MODE = Merge Supplier
    ATTR_CONFLICT_RES = Use Requestor
    IGNORE_NULLS = No
    JOIN_KEYS = @Value(bal_objektidentitet) @Value(UUID) AUTO
    MERGE_TYPE = Attributes Only
    PROCESS_DUPS = NO
    REJECT_NULL_MISSING_KEYS = No
    SUPPLIERS_FIRST = No
    MERGED -> AttributeManager
AttributeManager
    ATTR_TABLE:
      REMOVE bal_objektidentitet
      RENAME_SET_VALUE UUID > uuid
      SET_TO DatasetName = byggnad_y
    -> fastighet_y01 (writer SDF3_1)
    -> Junction_12
    -> Table1 (writer POSTGIS_1)
    -> Shapefile1 (writer SHAPEFILE_1)
Note: <@Value(DatasetName)>: [SHAPEFILE]
Shapefile1 (writer SHAPEFILE_1)
    attributes: uuid char(200), kom_bid char(200)
fastighet_y01 (writer SDF3_1)
    attributes: uuid char(200), kom_bid char(200)
Table1 (writer POSTGIS_1)
    attributes: uuid varchar(200), kom_bid varchar(200)
FeatureReader_4
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> ArcStrokerRefiner2D_3
ArcStrokerRefiner2D_3
    -> AttributeExposer_3
AttributeExposer_3
    ATTR_LIST = rk_fnr_fr,rk_trakt,rk_block_enhet,rk_omrade,rk_fastighet
    -> AttributeManager_2
AttributeManager_2
    ATTR_TABLE:
      RENAME_SET_VALUE rk_fnr_fr > fnr
      RENAME_SET_VALUE rk_trakt > trakt
      RENAME_SET_VALUE rk_block_enhet > blockenhet
      RENAME_SET_VALUE rk_omrade > omrade
      RENAME_SET_VALUE rk_fastighet > fastighet
      SET_TO DatasetName = fastighet_y
    -> fastighet_y0100 (writer SDF3_1)
    -> Junction_12
    -> Table100 (writer POSTGIS_2)
    -> Shapefile100 (writer SHAPEFILE_1)
Junction_12
    -> Aggregator
Note: <@Value(DatasetName)>: [SHAPEFILE]
Shapefile100 (writer SHAPEFILE_1)
    attributes: fnr char(200), trakt char(200), blockenhet char(200), omrade char(200), fastighet char(200)
fastighet_y0100 (writer SDF3_1)
    attributes: fnr char(200), trakt char(200), blockenhet char(200), omrade char(200), fastighet char(200)
Table100 (writer POSTGIS_2)
    attributes: fnr varchar(200), trakt varchar(200), blockenhet varchar(200), omrade varchar(200), fastighet varchar(200)

Bookmark: Loggning
Note: AttributeCreator_12_-_FeatureMerger_3
Junction_2
    -> FeatureMerger_2 [SUPPLIER]
Note: AttributeCreator_12_-_FeatureMerger_3
Junction_4
    -> FeatureMerger_3 [SUPPLIER]
Junction_10
    -> FeatureMerger_6 [SUPPLIER]
Aggregator
    ACCUM_ATTRS_NAME = Use Attributes From One Feature
    AGGREGATE_TYPE = Homogeneous Collection (If Possible)
    COUNT_ATTR = Antal
    MODE = Geometry - Assemble One Level
    SEP = ,
    AGGREGATE -> AttributeCreator_7
AttributeCreator_7
    ATTR_TABLE = SET_TO _FeatureIdMerger = 1
    -> FeatureMerger_6 [REQUESTOR]
FeatureMerger_6
    ATTR_ACCUM_MODE = Merge Supplier
    ATTR_CONFLICT_RES = Use Requestor
    IGNORE_NULLS = No
    JOIN_KEYS = @Value(_FeatureIdMerger) @Value(_FeatureIdMerger) AUTO
    MERGE_TYPE = Attributes Only
    PROCESS_DUPS = NO
    REJECT_NULL_MISSING_KEYS = No
    SUPPLIERS_FIRST = No
    MERGED -> StringConcatenator_5
StringConcatenator_5
    ACTION = Create New Attribute
    PARM_LINE = Process @Value(ProcessName) har färdigbehandlat @Value(Antal) st. objekt.
    VAL_ATTR = Logg
    -> DTStamperYYYY-MM-DD_HH:MI:SS.sss_5
DTStamperYYYY-MM-DD_HH:MI:SS.sss_5
    -> Logg_5
Logg_5: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,KLART,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: Följande kolumn förekommer fler än / en gång för specifikt dataset
Aggregator_4
    ACCUM_ATTRS_NAME = Use Attributes From One Feature
    AGGREGATE_TYPE = Homogeneous Collection (If Possible)
    COUNT_ATTR = Antal
    GROUP_BY = dl_new_column_name
    MODE = Geometry - Assemble One Level
    SEP = ", "
    AGGREGATE -> AttributeCreator_4
AttributeCreator_4
    ATTR_TABLE = SET_TO _FeatureIdMerger = 1
    -> FeatureMerger_3 [REQUESTOR]
FeatureMerger_3
    ATTR_ACCUM_MODE = Merge Supplier
    ATTR_CONFLICT_RES = Use Requestor
    IGNORE_NULLS = No
    JOIN_KEYS = @Value(_FeatureIdMerger) @Value(_FeatureIdMerger) AUTO
    MERGE_TYPE = Attributes Only
    PROCESS_DUPS = NO
    REJECT_NULL_MISSING_KEYS = No
    SUPPLIERS_FIRST = No
    MERGED -> StringConcatenator_6
StringConcatenator_6
    ACTION = Create New Attribute
    PARM_LINE = Följande @Value(Antal)  st. kolumner finns det dubbletter för (@Value(dl_new_column_name)). För att exporterad data vara läsbar enligt manifest, ändra kolumnnamn i manifest.
    VAL_ATTR = Logg
    -> DTStamperYYYY-MM-DD_HH:MI:SS.sss_2
DTStamperYYYY-MM-DD_HH:MI:SS.sss_2
    -> Logg_3
Logg_3: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: Endast till för som signal att starta logg
Sampler_2
    RATE = 1
    SAMPLE_MODE = No
    SAMPLE_TYPE_LONG = First N Features
    SAMPLED -> AttributeCreator_13
AttributeCreator_13
    ATTR_TABLE = SET_TO _FeatureIdMerger = 1
    -> FeatureMerger_2 [REQUESTOR]
FeatureMerger_2
    ATTR_ACCUM_MODE = Merge Supplier
    ATTR_CONFLICT_RES = Use Requestor
    IGNORE_NULLS = No
    JOIN_KEYS = @Value(_FeatureIdMerger) @Value(_FeatureIdMerger) AUTO
    MERGE_TYPE = Attributes Only
    PROCESS_DUPS = NO
    REJECT_NULL_MISSING_KEYS = No
    SUPPLIERS_FIRST = No
    MERGED -> StringConcatenator_2
StringConcatenator_2
    ACTION = Create New Attribute
    PARM_LINE = Kör @Value(ProcessName) för data definierad i "$(SchemaFlush)" till datalagret.
    VAL_ATTR = Logg
    -> DTStamperYYYY-MM-DD_HH:MI:SS.sss
DTStamperYYYY-MM-DD_HH:MI:SS.sss
    -> Logg_2
Logg_2: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,INFORMATION,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)

Bookmark: Kontrollera om kolumnnamn förekommer fler än en gång per dataset
Tester_2
    BOOL_OP = COMPOSITE
    COMPOSITE_TEST = 1 AND 2
    TEST_CLAUSE:
      TEST @Value(dl_need_new_column_name) = true
      TEST @Value(dl_new_column_name) ATTRIBUTE_HAS_VALUE ""
    TEST_MODE = TEST
    PASSED -> AttributeCreator
AttributeCreator
    ATTR_TABLE = SET_TO column_name = @Value(dl_new_column_name)
    -> Aggregator_2
Aggregator_2
    ACCUM_ATTRS_NAME = Use Attributes From One Feature
    AGGREGATE_TYPE = Homogeneous Collection (If Possible)
    COUNT_ATTR = AntalSameColumns
    GROUP_BY = fme_feature_type_name dl_new_column_name
    MODE = Geometry - Assemble One Level
    SEP = ,
    AGGREGATE -> Tester_3
Tester_3
    BOOL_OP = OR
    COMPOSITE_TEST = 1
    TEST_CLAUSE = TEST @Value(AntalSameColumns) > 1
    TEST_MODE = TEST
    PASSED -> Aggregator_4

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    INCLUDE_OFFSET = NO
    STAMP_TYPE = datetime
    TIMEZONE = local
    -> DateTimeConverter
DateTimeConverter
    DATETIME_ATTR = _dts
    OUT_FORMAT = %Y-%m-%d %H:%M:%S
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    NO_MATCH = _FME_NO_OP_
    REGEXP = YES
    SRC_ATTRS = _dts
    -> StringReplacer_2
StringReplacer_2
    CASE = NO
    FIND_TEXT = .*\.
    NO_MATCH = _FME_NO_OP_
    REGEXP = YES
    SRC_ATTRS = _mils
    -> SubstringExtractor
SubstringExtractor
    END = 2
    RESULT_ATTR = _subMils
    SRC_STRING = @Value(_mils)
    START = 0
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)

FME custom transformer ArcStrokerRefiner2D

Input (input)
    -> ArcStroker
Note: ArcStroker [ArcStroker Version 5] / General: / Stroke By: Maximum Deviation / Maximum Deviation: 0.02 / Make Polygon Out of 360 Degree Arcs: No
ArcStroker
    MAKE_POLY = No
    STROKE_CHOICE = Maximum Deviation
    TOLERANCE_VAL = 0.02
    STROKED -> 2DForcer
2DForcer
    2D -> GeometryRefiner
GeometryRefiner
    -> Output (output)
Output (output)
