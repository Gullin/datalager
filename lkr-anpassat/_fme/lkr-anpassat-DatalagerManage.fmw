FME workspace lkr-anpassat-DatalagerManage.fmw

Parameters:
- RotDirectory = ../   # Katalogen där processen startar
- ProcessName =   # Processnamn
- OutputDirectory = C:\dev\Datalager_procsrc\_geodatarepo\landskrona\lkr_gis   # Katalog för lagring av del av datalager
- ProcessModulName =   # Processmodulsnamn
- IsWholeProcessRun = 1   # Är hela datalagerprocessen körd
- FME_USER_PARAM_PRIVATE_GRP =   # Private Parameters
- Manifest = $(RotDirectory)$(ProcessModulName)/_schema/schema-manifest.xlsx   # Manifest (export- och schema-specifikation)
- SchemaFlush = $(RotDirectory)$(ProcessModulName)/_schema/schema-flush.xlsx   # Schemaspecifikation för aktuellt data
- PG_SCHEMA =   # PostgreSQL Schema
- PARAMETER_4 = FME_DISCLOSURE_OPEN   # Databasanslutningar
- DestDataset_POSTGIS = PG_DATALAGER   # Connection
- OutSchemaFileNameSuffix = flush   # Suffix på filnamn för schemalistning (skapas med bindestreck)
- PlandokumentDir =   # Katalog plandokument
- PlandokumentFileFilter =   # Filfilter
- PlandokumentDir3Rd =   # Katalog plandokument 3:e
- DestDataset_POSTGIS_23 = PG_DATALAGER_ADMSRV0118   # Connection
- DestDataset_POSTGIS_27 = PG_DATALAGER   # Connection
- DestDataset_POSTGIS_31 = PG_DATALAGER_ADMSRV0118   # Connection
- DestDataset_POSTGIS_25 = PG_DATALAGER   # Connection
- DestDataset_POSTGIS_29 = PG_DATALAGER_ADMSRV0118   # Connection
- DestDataset_POSTGIS_33 = PG_DATALAGER   # Connection
- DestDataset_POSTGIS_24 = PG_DATALAGER   # Connection
- DestDataset_POSTGIS_26 = PG_DATALAGER_ADMSRV0118   # Connection
- DestDataset_POSTGIS_28 = PG_DATALAGER_ADMSRV0118   # Connection
- DestDataset_POSTGIS_30 = PG_DATALAGER   # Connection
- DestDataset_POSTGIS_32 = PG_DATALAGER_ADMSRV0118   # Connection

Readers:
- XLSXR_1: XLSXR from $(SchemaFlush)
- SCHEMA_FROM_TABLE_1: SCHEMA_FROM_TABLE from $(Manifest)

Writers:
- SDF3_1: SDF3 to $(OutputDirectory) in EPSG:3008
- SHAPEFILE_1: SHAPEFILE to $(OutputDirectory) in EPSG:3008
- FILECOPY_1: FILECOPY
- POSTGIS_1: POSTGIS to $(DestDataset_POSTGIS) in EPSG:3008
- POSTGIS_2: POSTGIS to $(DestDataset_POSTGIS) in EPSG:3008
- POSTGIS_3: POSTGIS to $(DestDataset_POSTGIS) in EPSG:3008
- POSTGIS_4: POSTGIS to $(DestDataset_POSTGIS) in EPSG:3008
- POSTGIS_5: POSTGIS to $(DestDataset_POSTGIS) in EPSG:3008
- POSTGIS_6: POSTGIS to $(DestDataset_POSTGIS) in EPSG:3008
- POSTGIS_7: POSTGIS to $(DestDataset_POSTGIS_27) in EPSG:3008
- POSTGIS_8: POSTGIS to $(DestDataset_POSTGIS_25) in EPSG:3008
- POSTGIS_9: POSTGIS to $(DestDataset_POSTGIS_33) in EPSG:3008
- POSTGIS_10: POSTGIS to $(DestDataset_POSTGIS_24) in EPSG:3008
- POSTGIS_11: POSTGIS to $(DestDataset_POSTGIS_30) in EPSG:3008
- POSTGIS_12: POSTGIS to $(DestDataset_POSTGIS_23) in EPSG:3008
- POSTGIS_13: POSTGIS to $(DestDataset_POSTGIS_23) in EPSG:3008
- POSTGIS_14: POSTGIS to $(DestDataset_POSTGIS_23) in EPSG:3008
- POSTGIS_15: POSTGIS to $(DestDataset_POSTGIS_23) in EPSG:3008
- POSTGIS_16: POSTGIS to $(DestDataset_POSTGIS_23) in EPSG:3008
- POSTGIS_17: POSTGIS to $(DestDataset_POSTGIS_23) in EPSG:3008
- POSTGIS_18: POSTGIS to $(DestDataset_POSTGIS_31) in EPSG:3008
- POSTGIS_19: POSTGIS to $(DestDataset_POSTGIS_29) in EPSG:3008
- POSTGIS_20: POSTGIS to $(DestDataset_POSTGIS_26) in EPSG:3008
- POSTGIS_21: POSTGIS to $(DestDataset_POSTGIS_28) in EPSG:3008
- POSTGIS_22: POSTGIS to $(DestDataset_POSTGIS_32) in EPSG:3008
- OGCGEOPACKAGE_1: OGCGEOPACKAGE to $(OutputDirectory) in EPSG:3008

Note: Parametrar / * [RotDirectory] Kommer från batch-processen och är obligatoriskt för alla FME-processor. / * [ProcessName] Kommer från batch-processen och är obligatoriskt för alla FME-processor. / * [Manifest] Excel-fil från ett tidigare exporterat schema anpassad med nya kolumnnamn samt vilken data som ska exporteras. / * [OutputDirectory] Katalogsökväg för exporterad geodata (delrepository).
schema (reader XLSXR_1)
    attributes: fme_feature_type_name char(20), column_name char(16), dl_need_new_column_name char(6), dl_new_column_name char(12), dl_export char(5), fme_data_type char(18), native_data_type char(14), fme_format_long_name char(22), fme_format_short_name char(15), _dirpath char(1), _extension char(1), DatasetFull char(8), Dataset char(8), column_name_char_length number(3,0)
    -> Tester_4
Tester_4
    BOOL_OP = OR
    TEST_CLAUSE = TEST @Value(dl_export) = true
    TEST_MODE = TEST
    PASSED -> Tester_2
    PASSED -> Aggregator_3
    PASSED -> Sampler_2
Aggregator_3
    ACCUM_ATTRS_NAME = Drop Incoming Attributes
    AGGREGATE_TYPE = Homogeneous Collection (If Possible)
    GROUP_BY = fme_feature_type_name fme_format_short_name Dataset
    MODE = Geometry - Assemble One Level
    SEP = ,
    AGGREGATE -> StringConcatenator
    AGGREGATE -> AttributeCopier
StringConcatenator [off]
    ACTION = Create New Attribute
    PARM_LINE = @Value(Dataset).@Value(fme_feature_type_name)
    VAL_ATTR = _filterValue
    -> StringCaseChanger
AttributeCopier
    ATTR_TABLE = COPY fme_feature_type_name > _filterValue
    MISSING_INPUT_ATTRS = REMOVE
    -> StringCaseChanger
StringCaseChanger
    ATTRCHOICE = Selected Attributes
    ATTRLIST = _filterValue
    CHANGE_TYPE = lowercase
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(_filterValue) = ex_special.eg_omrade_y",ex_special.eg_omrade_y,"BOOL_OP,OR,COMPOSITE_TEST,""""""1"""""",TEST_CLAUSE,TEST @Value(_filterValue) = td_bal.bal_adressplats_p",td_bal.bal_adressplats_p,"BOOL_OP,OR,COMPOSITE_TEST,""""""1"""""",TEST_CLAUSE,TEST @Value(_filterValue) = td_bal.bal_byggnad_y",td_bal.bal_byggnad_y,"BOOL_OP,OR,COMPOSITE_TEST,""""""1"""""",TEST_CLAUSE,TEST @Value(_filterValue) = td_baskarta.ma_markanvandningyta_y",td_baskarta.ma_markanvandningyta_y,"BOOL_OP,OR,COMPOSITE_TEST,""""""1"""""",TEST_CLAUSE,TEST @Value(_filterValue) = td_baskarta.md_markdetalj_l",td_baskarta.md_markdetalj_l,"BOOL_OP,OR,COMPOSITE_TEST,""""""1"""""",TEST_CLAUSE,TEST @Value(_filterValue) = td_baskarta.md_markdetalj_y",td_baskarta.md_markdetalj_y,"BOOL_OP,OR,COMPOSITE_TEST,""""""1"""""",TEST_CLAUSE,TEST @Value(_filterValue) = td_baskarta.mt_marktackeyta_y",td_baskarta.mt_marktackeyta_y,"BOOL_OP,OR,COMPOSITE_TEST,""""""1"""""",TEST_CLAUSE,TEST @Value(_filterValue) = td_baskarta.td_namn_p",td_baskarta.td_namn_p,"BOOL_OP,OR,COMPOSITE_TEST,""""""1"""""",TEST_CLAUSE,TEST @Value(_filterValue) = td_detaljplan.dp_anvandningbest_y",td_detaljplan.dp_anvandningbest_y,"BOOL_OP,OR,COMPOSITE_TEST,""""""1"""""",TEST_CLAUSE,TEST @Value(_filterValue) = td_detaljplan.dp_dt_anvandningtyp",td_detaljplan.dp_dt_anvandningtyp,"BOOL_OP,OR,COMPOSITE_TEST,""""""1"""""",TEST_CLAUSE,TEST @Value(_filterValue) = td_detaljplan.td_an_dt_verksamhet_1",td_detaljplan.td_an_dt_verksamhet_1,"BOOL_OP,OR,COMPOSITE_TEST,""""""1"""""",TEST_CLAUSE,TEST @Value(_filterValue) = td_detaljplan.eg_dt_anvandning_allman_platsmark",td_detaljplan.eg_dt_anvandning_allman_platsmark,"BOOL_OP,OR,COMPOSITE_TEST,""""""1"""""",TEST_CLAUSE,TEST @Value(_filterValue) = td_detaljplan.eg_dt_anvandning_kvartersmark",td_detaljplan.eg_dt_anvandning_kvartersmark,"BOOL_OP,OR,COMPOSITE_TEST,""""""1"""""",TEST_CLAUSE,TEST @Value(_filterValue) = td_drk.rk_fastighet_y",td_drk.rk_fastighet_y,"BOOL_OP,OR,COMPOSITE_TEST,""""""1"""""",TEST_CLAUSE,TEST @Value(_filterValue) = dbo.off_fir_fastigh",dbo.off_fir_fastigh,"BOOL_OP,OR,COMPOSITE_TEST,""""""1"""""",TEST_CLAUSE,TEST @Value(_filterValue) = dbo.off_fir_foratt_status",dbo.off_fir_foratt_status,"BOOL_OP,OR,COMPOSITE_TEST,""""""1"""""",TEST_CLAUSE,TEST @Value(_filterValue) = dbo.fb_fir_lagfart",dbo.fb_fir_lagfart,"BOOL_OP,OR,COMPOSITE_TEST,""""""1"""""",TEST_CLAUSE,TEST @Value(_filterValue) = dbo.tax_taxpers",dbo.tax_taxpers,"BOOL_OP,OR,COMPOSITE_TEST,""""""1"""""",TEST_CLAUSE,TEST @Value(_filterValue) = dbo.fir_firkoder",dbo.fir_firkoder,"BOOL_OP,OR,COMPOSITE_TEST,""""""1"""""",TEST_CLAUSE,TEST @Value(_filterValue) = td_drk.rk_plan_y",td_drk.rk_plan_y,"BOOL_OP,OR,COMPOSITE_TEST,""""""1"""""",TEST_CLAUSE,TEST @Value(_filterValue) = td_drk.rk_plan_y_info",td_drk.rk_plan_y_info,"BOOL_OP,OR,COMPOSITE_TEST,""""""1"""""",TEST_CLAUSE,TEST @Value(_filterValue) = dbo.off_fir_plan",dbo.off_fir_plan,"BOOL_OP,OR,COMPOSITE_TEST,""""""1"""""",TEST_CLAUSE,TEST @Value(_filterValue) = dbo.off_fir_plan_beslut",dbo.off_fir_plan_beslut,"BOOL_OP,OR,COMPOSITE_TEST,""""""1"""""",TEST_CLAUSE,TEST @Value(_filterValue) = dbo.fir_plan_egnauppg",dbo.fir_plan_egnauppg,"BOOL_OP,OR,COMPOSITE_TEST,""""""1"""""",TEST_CLAUSE,TEST @Value(_filterValue) = dbo.off_fir_plan_kommun",dbo.off_fir_plan_kommun,"BOOL_OP,OR,COMPOSITE_TEST,""""""1"""""",TEST_CLAUSE,TEST @Value(_filterValue) = dbo.off_fir_plan_hanvisn",dbo.off_fir_plan_hanvisn,"BOOL_OP,OR,COMPOSITE_TEST,""""""1"""""",TEST_CLAUSE,TEST @Value(_filterValue) = dbo.off_fir_plan_hanvtext",dbo.off_fir_plan_hanvtext,"BOOL_OP,OR,COMPOSITE_TEST,""""""1"""""",TEST_CLAUSE,TEST @Value(_filterValue) = td_drk.rk_ga_l",td_drk.rk_ga_l,"BOOL_OP,OR,COMPOSITE_TEST,""""""1"""""",TEST_CLAUSE,TEST @Value(_filterValue) = td_drk.rk_ga_p",td_drk.rk_ga_p,"BOOL_OP,OR,COMPOSITE_TEST,""""""1"""""",TEST_CLAUSE,TEST @Value(_filterValue) = td_drk.rk_ga_y",td_drk.rk_ga_y,"BOOL_OP,OR,COMPOSITE_TEST,""""""1"""""",TEST_CLAUSE,TEST @Value(_filterValue) = dbo.off_fir_andamal",dbo.off_fir_andamal,"BOOL_OP,OR,COMPOSITE_TEST,""""""1"""""",TEST_CLAUSE,TEST @Value(_filterValue) = td_drk.rk_rattighet_l",td_drk.rk_rattighet_l,"BOOL_OP,OR,COMPOSITE_TEST,""""""1"""""",TEST_CLAUSE,TEST @Value(_filterValue) = td_drk.rk_rattighet_p",td_drk.rk_rattighet_p,"BOOL_OP,OR,COMPOSITE_TEST,""""""1"""""",TEST_CLAUSE,TEST @Value(_filterValue) = td_drk.rk_rattighet_y",td_drk.rk_rattighet_y,"BOOL_OP,OR,COMPOSITE_TEST,""""""1"""""",TEST_CLAUSE,TEST @Value(_filterValue) = dbo.off_fir_rattigh",dbo.off_fir_rattigh
    ex_special.eg_omrade_y -> Junction_24
    td_bal.bal_adressplats_p -> FeatureReader_4 [INITIATOR]
    td_bal.bal_byggnad_y -> Junction_24
    td_baskarta.ma_markanvandningyta_y -> Junction_24
    td_baskarta.md_markdetalj_l -> Junction_24
    td_baskarta.md_markdetalj_y -> Junction_24
    td_baskarta.mt_marktackeyta_y -> Junction_24
    td_baskarta.td_namn_p -> Junction_24
    td_detaljplan.dp_anvandningbest_y -> Junction_15
    td_detaljplan.dp_dt_anvandningtyp -> Junction_15
    td_detaljplan.td_an_dt_verksamhet_1 -> Junction_15
    td_detaljplan.eg_dt_anvandning_allman_platsmark -> Junction_15
    td_detaljplan.eg_dt_anvandning_kvartersmark -> Junction_15
    td_drk.rk_fastighet_y -> Junction_5
    dbo.off_fir_fastigh -> Junction_5
    dbo.off_fir_foratt_status -> Junction_5
    dbo.fb_fir_lagfart -> Junction_5
    dbo.tax_taxpers -> Junction_5
    dbo.fir_firkoder -> Junction_6
    td_drk.rk_plan_y -> Junction_6
    td_drk.rk_plan_y_info -> Junction_6
    dbo.off_fir_plan -> Junction_6
    dbo.off_fir_plan_beslut -> Junction_6
    dbo.fir_plan_egnauppg -> Junction_6
    dbo.off_fir_plan_kommun -> Junction_6
    dbo.off_fir_plan_hanvisn -> Junction_6
    dbo.off_fir_plan_hanvtext -> Junction_6
    td_drk.rk_ga_l -> Junction_18
    td_drk.rk_ga_p -> Junction_18
    td_drk.rk_ga_y -> Junction_18
    dbo.off_fir_andamal -> Junction_18
    td_drk.rk_rattighet_l -> Junction_19
    td_drk.rk_rattighet_p -> Junction_19
    td_drk.rk_rattighet_y -> Junction_19
    dbo.off_fir_rattigh -> Junction_19
Junction_24
    -> Search
FeatureReader_4
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> ArcStrokerRefiner2D
ArcStrokerRefiner2D
    -> AttributeExposer
AttributeExposer
    ATTR_LIST = bal_objektidentitet,bal_nummer,bal_bokstavstillagg,bal_lagestillagg,bal_tillaggsnummer,bal_typ,bal_insamlingslage,bal_belagenhetsstatus,bal_objektstatus,bal_postnummer,bal_postort,bal_namn,td_adressomradesnamn,td_gardsadressomradesnamn,td_adress,td_gardsadress,td_nummer_bokstav
    -> AttributeExposer_2
    -> Search
Search
    DATASET = @Value(Dataset)
    FME_FEATURE_TYPE_NAME = @Value(fme_feature_type_name)
    OutSchemaFileNameSuffix = flush
    RotDirectory = ../
    _FILTERVALUE = @Value(_filterValue)
    -> StringConcatenator_36
    <Rejected> -> TestFilter
StringConcatenator_36
    ACTION = Create New Attribute
    PARM_LINE = fme_basicstring:13%23:@Value(_name)@Value(_name_extension)
    VAL_ATTR = DatasetName
    -> ArcStrokerRefiner2D_19
ArcStrokerRefiner2D_19
    -> AttributeKeeper_5
AttributeKeeper_5
    CREATE_BULK_MODE_FEATURES = NO
    KEEP_ATTRS = DatasetName,source,text,typ
    -> GeometryFilter
    -> fastighet_y010000 (writer SDF3_1)
    -> Table1 (writer POSTGIS_11)
    -> Table1 (writer POSTGIS_22)
    -> SchemaManipulation_3 [Feature]
    -> Junction_31
GeometryFilter
    BREAK_AGG = No
    GEOM_PORT_NAMES = Point Area
    POINT -> Shapefile101 (writer SHAPEFILE_1)
    AREA -> Shapefile10100 (writer SHAPEFILE_1)
SchemaManipulation_3
    DATASETNAME = @Value(DatasetName)
    Output_Gpkg_Dataset -> Table1 (writer OGCGEOPACKAGE_1)
Note: Junction_12 : Input
Junction_31
    -> Junction_32
Note: AttributeKeeper_5 : Output
Junction_32
    -> Junction_12
AttributeExposer_2
    ATTR_LIST = fme_feature_type_name,fme_feature_type
    -> AttributeCreator_23
AttributeCreator_23
    ATTR_TABLE:
      SET_TO fme_feature_type_name = adress
      SET_TO fme_feature_type = adress
    -> AttributeCreator_24
AttributeCreator_24
    ATTR_TABLE = SET_TO _name_extension = _belagenhetsadress
    -> StringConcatenator_23
StringConcatenator_23
    ACTION = Create New Attribute
    PARM_LINE = fme_basicstring:24%23%2:@Value(fme_feature_type)@Value(_name_extension)_p
    VAL_ATTR = DatasetName
    -> AttributeManager
AttributeManager
    ATTR_TABLE:
      RENAME_SET_VALUE bal_objektidentitet > objid
      RENAME_SET_VALUE bal_nummer > nr
      RENAME_SET_VALUE bal_bokstavstillagg > littera
      RENAME_SET_VALUE bal_lagestillagg > lagtillagg
      RENAME_SET_VALUE bal_tillaggsnummer > tillaggnr
      RENAME_SET_VALUE bal_typ > typ
      RENAME_SET_VALUE bal_insamlingslage > insamlage
      RENAME_SET_VALUE bal_belagenhetsstatus > belstatus
      RENAME_SET_VALUE bal_objektstatus > objstatus
      RENAME_SET_VALUE bal_postnummer > postnr
      RENAME_SET_VALUE bal_postort > postort
      RENAME_SET_VALUE bal_namn > namn
      RENAME_SET_VALUE td_adressomradesnamn > adromr
      RENAME_SET_VALUE td_gardsadressomradesnamn > gardadromr
      RENAME_SET_VALUE td_adress > adress
      RENAME_SET_VALUE td_gardsadress > gardadress
      RENAME_SET_VALUE td_nummer_bokstav > nr_littera
      REMOVE _name_extension
      REMOVE fme_feature_type_name
      REMOVE fme_feature_type
    -> AttributeKeeper_6
AttributeKeeper_6
    CREATE_BULK_MODE_FEATURES = NO
    KEEP_ATTRS = adress,adromr,belstatus,DatasetName,gardadress,gardadromr,insamlage,lagtillagg,littera,namn,nr,nr_littera,objid,objstatus,postnr,postort,tillaggnr,typ
    -> SchemaManipulation_2 [Feature]
    -> Table1 (writer POSTGIS_6)
    -> Table1 (writer POSTGIS_17)
    -> fastighet_y0100 (writer SDF3_1)
    -> Junction_29
    -> Shapefile1 (writer SHAPEFILE_1)
SchemaManipulation_2
    DATASETNAME = @Value(DatasetName)
    Output_Gpkg_Dataset -> Table1 (writer OGCGEOPACKAGE_1)
Note: Junction_12 : Input
Junction_29
    -> Junction_30
Note: AttributeKeeper_6 : Output
Junction_30
    -> Junction_12
Junction_15
    -> Detaljplanemosaik_användning
Detaljplanemosaik_användning
    DATASET = @Value(Dataset)
    FME_FEATURE_TYPE_NAME = @Value(fme_feature_type_name)
    FME_FORMAT_SHORT_NAME = @Value(fme_format_short_name)
    OutSchemaFileNameSuffix = flush
    RotDirectory = ../
    _FILTERVALUE = @Value(_filterValue)
    -> ArcStrokerRefiner2D_2
ArcStrokerRefiner2D_2
    -> AttributeCreator_3
AttributeCreator_3
    ATTR_TABLE = SET_TO _name_extension
    -> StringConcatenator_22
StringConcatenator_22
    ACTION = Create New Attribute
    PARM_LINE = @Value(fme_feature_type)@Value(_name_extension)_y
    VAL_ATTR = DatasetName
    -> AttributeRemover
AttributeRemover
    REMOVE_ATTRS = _name_extension,fme_feature_type,fme_feature_type_name
    -> Table1 (writer POSTGIS_5)
    -> Table1 (writer POSTGIS_12)
    -> fastighet_y01 (writer SDF3_1)
    -> Shapefile100 (writer SHAPEFILE_1)
    -> Junction_33
    -> SchemaManipulation_4 [Feature]
SchemaManipulation_4
    DATASETNAME = @Value(DatasetName)
    Output_Gpkg_Dataset -> Table1 (writer OGCGEOPACKAGE_1)
Note: Junction_12 : Input
Junction_33
    -> Junction_34
Note: AttributeRemover : Output
Junction_34
    -> Junction_12
Junction_5
    -> Fastighet
Fastighet
    DATASET = @Value(Dataset)
    FME_FEATURE_TYPE_NAME = @Value(fme_feature_type_name)
    FME_FORMAT_SHORT_NAME = @Value(fme_format_short_name)
    OutSchemaFileNameSuffix = flush
    RotDirectory = ../
    _FILTERVALUE = @Value(_filterValue)
    Kommunyta -> AttributeCreator_41
    Kvarter_Trakter -> AttributeCreator_40
    Grunddata -> AttributeCreator_5
    Forrattning -> AttributeCreator_8
    Agare -> AttributeCreator_9
    Landskrona_stad -> AttributeCreator_10
    Landskrona_stad_lagfart -> AttributeCreator_11
    Landskrona_stad_lagfart_tomtratt -> AttributeCreator_14
    Landskrona_stad_lagfart_ej_tomtratt -> AttributeCreator_15
    Landskrona_stad_lagfart_taxering -> AttributeCreator_16
    <Rejected> -> AttributeCreator_6
AttributeCreator_41
    ATTR_TABLE = SET_TO _name_extension
    -> StringConcatenator_35
StringConcatenator_35
    ACTION = Create New Attribute
    PARM_LINE = @Value(fme_feature_type)@Value(_name_extension)_y
    VAL_ATTR = DatasetName
    -> ArcStrokerRefiner2D_17
ArcStrokerRefiner2D_17
    -> AttributeKeeper_2
AttributeKeeper_2
    CREATE_BULK_MODE_FEATURES = NO
    KEEP_ATTRS = DatasetName
    -> Shapefile10001 (writer SHAPEFILE_1)
    -> fastighet_y0101 (writer SDF3_1)
    -> Table1 (writer POSTGIS_9)
    -> Table1 (writer POSTGIS_20)
    -> Junction_35
    -> SchemaManipulation_5 [Feature]
SchemaManipulation_5
    DATASETNAME = @Value(DatasetName)
    Output_Gpkg_Dataset -> Table1 (writer OGCGEOPACKAGE_1)
Note: Junction_12 : Input
Junction_35
    -> Junction_36
Note: AttributeKeeper_2 : Output
Junction_36
    -> Junction_12
AttributeCreator_40
    ATTR_TABLE = SET_TO _name_extension
    -> StringConcatenator_34
StringConcatenator_34
    ACTION = Create New Attribute
    PARM_LINE = fme_basicstring:24%23%3:@Value(fme_feature_type)@Value(_name_extension)_my
    VAL_ATTR = DatasetName
    -> ArcStrokerRefiner2D_18
ArcStrokerRefiner2D_18
    -> AttributeKeeper_4
AttributeKeeper_4
    CREATE_BULK_MODE_FEATURES = NO
    KEEP_ATTRS = DatasetName,typ,namn_icap,namn_vers,namn_wcap
    -> Shapefile10002 (writer SHAPEFILE_1)
    -> fastighet_y0102 (writer SDF3_1)
    -> Table1 (writer POSTGIS_10)
    -> Table1 (writer POSTGIS_21)
    -> Junction_37
    -> SchemaManipulation_6 [Feature]
SchemaManipulation_6
    DATASETNAME = @Value(DatasetName)
    Output_Gpkg_Dataset -> Table1 (writer OGCGEOPACKAGE_1)
Note: Junction_12 : Input
Junction_37
    -> Junction_38
Note: AttributeKeeper_4 : Output
Junction_38
    -> Junction_12
AttributeCreator_5
    ATTR_TABLE = SET_TO _name_extension
    -> StringConcatenator_4
StringConcatenator_4
    ACTION = Create New Attribute
    PARM_LINE = @Value(fme_feature_type)@Value(_name_extension)_y
    VAL_ATTR = DatasetName
    -> ArcStrokerRefiner2D_3
AttributeCreator_8
    ATTR_TABLE = SET_TO _name_extension = _forrattning
    -> StringConcatenator_9
StringConcatenator_9
    ACTION = Create New Attribute
    PARM_LINE = @Value(fme_feature_type)@Value(_name_extension)_y
    VAL_ATTR = DatasetName
    -> ArcStrokerRefiner2D_3
ArcStrokerRefiner2D_3
    -> AttributeKeeper
AttributeKeeper
    CREATE_BULK_MODE_FEATURES = NO
    KEEP_ATTRS = fastighet,forratt,tomtrat,fast_id,regnr,omrade,trakt,lagfart,DatasetName,dep,uuid
    -> fastighet_y (writer SDF3_1)
    -> Shapefile10000 (writer SHAPEFILE_1)
    -> schema (writer POSTGIS_1)
    -> Table1 (writer POSTGIS_13)
    -> Junction_39
    -> SchemaManipulation [Feature]
Note: OBS! / Fungerar ej med samma skrivare till PostGIS. FME kraschar och registrerar inte alla dataset korrekt.
SchemaManipulation
    DATASETNAME = @Value(DatasetName)
    Output_Gpkg_Dataset -> Table1 (writer OGCGEOPACKAGE_1)
Note: Junction_12 : Input
Junction_39
    -> Junction_40
Note: AttributeKeeper : Output
Junction_40
    -> Junction_12
AttributeCreator_9
    ATTR_TABLE = SET_TO _name_extension = _lagtax
    -> StringConcatenator_10
StringConcatenator_10
    ACTION = Create New Attribute
    PARM_LINE = @Value(fme_feature_type)@Value(_name_extension)_y
    VAL_ATTR = DatasetName
    -> ArcStrokerRefiner2D_4
AttributeCreator_10
    ATTR_TABLE = SET_TO _name_extension = _lagtax_lkr
    -> StringConcatenator_11
StringConcatenator_11
    ACTION = Create New Attribute
    PARM_LINE = @Value(fme_feature_type)@Value(_name_extension)_y
    VAL_ATTR = DatasetName
    -> ArcStrokerRefiner2D_4
AttributeCreator_11
    ATTR_TABLE = SET_TO _name_extension = _lagtax_lkr_lag
    -> StringConcatenator_12
StringConcatenator_12
    ACTION = Create New Attribute
    PARM_LINE = @Value(fme_feature_type)@Value(_name_extension)_y
    VAL_ATTR = DatasetName
    -> ArcStrokerRefiner2D_4
AttributeCreator_14
    ATTR_TABLE = SET_TO _name_extension = _lagtax_lkr_lag_tomtr
    -> StringConcatenator_13
StringConcatenator_13
    ACTION = Create New Attribute
    PARM_LINE = @Value(fme_feature_type)@Value(_name_extension)_y
    VAL_ATTR = DatasetName
    -> ArcStrokerRefiner2D_4
AttributeCreator_15
    ATTR_TABLE = SET_TO _name_extension = _lagtax_lkr_lag_ejtomtr
    -> StringConcatenator_14
StringConcatenator_14
    ACTION = Create New Attribute
    PARM_LINE = @Value(fme_feature_type)@Value(_name_extension)_y
    VAL_ATTR = DatasetName
    -> ArcStrokerRefiner2D_4
AttributeCreator_16
    ATTR_TABLE = SET_TO _name_extension = _lagtax_lkr_tax
    -> StringConcatenator_15
StringConcatenator_15
    ACTION = Create New Attribute
    PARM_LINE = @Value(fme_feature_type)@Value(_name_extension)_y
    VAL_ATTR = DatasetName
    -> ArcStrokerRefiner2D_4
ArcStrokerRefiner2D_4
    -> AttributeKeeper_3
AttributeKeeper_3
    CREATE_BULK_MODE_FEATURES = NO
    KEEP_ATTRS = DatasetName,fastighet,l_enamn,tomtrat,l_mnamn,t_namn,t_fnamn,omrade,tx_ponr,t_enamn,l_fnamn,t_ponr,fast_id,trakt,l_ponr,l_tnamn,forratt,l_namn,tx_taxar,t_tnamn,t_mnamn,lagfart,regnr,dep,uuid
    -> fastighet_lagtax_y (writer SDF3_1)
    -> Table1 (writer POSTGIS_14)
    -> Shapefile1000000 (writer SHAPEFILE_1)
    -> Table1 (writer POSTGIS_2)
    -> Junction_41
    -> SchemaManipulation_7 [Feature]
SchemaManipulation_7
    DATASETNAME = @Value(DatasetName)
    Output_Gpkg_Dataset -> Table1 (writer OGCGEOPACKAGE_1)
Note: Junction_12 : Input
Junction_41
    -> Junction_42
Note: AttributeKeeper_3 : Output
Junction_42
    -> Junction_12
Junction_6
    -> Plan_och_Tomt
Plan_och_Tomt
    DATASET = @Value(Dataset)
    FME_FEATURE_TYPE_NAME = @Value(fme_feature_type_name)
    FME_FORMAT_SHORT_NAME = @Value(fme_format_short_name)
    OutSchemaFileNameSuffix = flush
    PlandokumentDir = $(PlandokumentDir)
    PlandokumentDir3Rd = $(PlandokumentDir3Rd)
    PlandokumentFileFilter = $(PlandokumentFileFilter)
    RotDirectory = ../
    _FILTERVALUE = @Value(_filterValue)
    Plandokument -> filecopy (writer FILECOPY_1)
    Plandokument -> StringConcatenator_24
    Planytor_gällande_alla -> ArcStrokerRefiner2D_5
    Planytor_gällande -> ArcStrokerRefiner2D_6
    Planytor_gällande_ändrade -> ArcStrokerRefiner2D_7
    Plancentroid_gällande_alla -> ArcStrokerRefiner2D_8
    Tomtindelning_Fastighetsplan_gällande -> ArcStrokerRefiner2D_9
    Tomtindelning_Fastighetsplan_centroid_gällande -> ArcStrokerRefiner2D_10
    <Rejected> -> AttributeCreator_22
Note: Ersatt med CmdCaller p.g.a. ERROR / MULTIi_WRITER FILECOPY_DATASET
filecopy (writer FILECOPY_1) [off]
    attributes: filecopy_source_dataset char(512), filecopy_dest_dataset char(512), filecopy_dest_filename char(128)
StringConcatenator_24
    ACTION = Create New Attribute
    PARM_LINE = fme_basicstring:25%31%3%29%30%1:ECHO F | XCOPY /Q /I /Y "@Value(filecopy_source_dataset)" "@Value(filecopy_dest_dataset)@Value(filecopy_dest_filename)"
    VAL_ATTR = cmd_copy_docs
    -> SystemCaller
SystemCaller
    ATTR = cmd_status_code
    CMD = @Value(cmd_copy_docs)
    -> Tester
Tester
    BOOL_OP = OR
    TEST_CLAUSE = TEST @Value(cmd_status_code) = 0
    TEST_MODE = TEST
    FAILED -> ConcatenatedSample_2 [StringAttribute]
ArcStrokerRefiner2D_5
    -> AttributeCreator_17
AttributeCreator_17
    ATTR_TABLE = SET_TO _name_extension = _alla
    -> StringConcatenator_16
    -> Aggregator_5
StringConcatenator_16
    ACTION = Create New Attribute
    PARM_LINE = @Value(fme_feature_type)@Value(_name_extension)_y
    VAL_ATTR = DatasetName
    -> Junction_11
Note: Aggregeras på alla attribut för att få multipolygon av / resp. plan med flera områden. / Behöver uppdateras vid förändring av attribut i processen.
Aggregator_5
    ACCUM_ATTRS_NAME = Use Attributes From One Feature
    AGGREGATE_TYPE = Homogeneous Collection (If Possible)
    GROUP_BY = d_genom_f plan_id harkvalpro d_beslut planavgift harpgbesk planfk d_senajou d_lagakra hargenom d_genom_t komkod status fme_feature_type_name akt_pb akt_egn fme_feature_type harpkarta plannamn d_gall_t _name_extension harbesk akt hartkarta harpbest statustxt pav_akt pav_p_id pav_akt_br pav_akt_n tradfallej avvik avvik_dok
    MODE = Geometry - Assemble One Level
    SEP = ,
    AGGREGATE -> StringConcatenator_8
StringConcatenator_8
    ACTION = Create New Attribute
    PARM_LINE = @Value(fme_feature_type)@Value(_name_extension)_my
    VAL_ATTR = DatasetName
    -> Junction_11
ArcStrokerRefiner2D_6
    -> AttributeCreator_18
AttributeCreator_18
    ATTR_TABLE = SET_TO _name_extension
    -> StringConcatenator_17
StringConcatenator_17
    ACTION = Create New Attribute
    PARM_LINE = @Value(fme_feature_type)@Value(_name_extension)_y
    VAL_ATTR = DatasetName
    -> Junction_11
ArcStrokerRefiner2D_7
    -> AttributeCreator_19
AttributeCreator_19
    ATTR_TABLE = SET_TO _name_extension = _andrade
    -> StringConcatenator_18
StringConcatenator_18
    ACTION = Create New Attribute
    PARM_LINE = @Value(fme_feature_type)@Value(_name_extension)_y
    VAL_ATTR = DatasetName
    -> Junction_11
Junction_11
    -> Table1 (writer POSTGIS_15)
    -> fastighet_y00 (writer SDF3_1)
    -> Table1 (writer POSTGIS_3)
    -> Shapefile100000000 (writer SHAPEFILE_1)
    -> Junction_43
    -> SchemaManipulation_8 [Feature]
SchemaManipulation_8
    DATASETNAME = @Value(DatasetName)
    Output_Gpkg_Dataset -> Table1 (writer OGCGEOPACKAGE_1)
Note: Junction_12 : Input
Junction_43
    -> Junction_44
Note: Junction_11 : Output
Junction_44
    -> Junction_12
ArcStrokerRefiner2D_8
    -> AttributeCreator_21
AttributeCreator_21
    ATTR_TABLE = SET_TO _name_extension = centroid_alla
    -> StringConcatenator_20
StringConcatenator_20
    ACTION = Create New Attribute
    PARM_LINE = @Value(fme_feature_type)@Value(_name_extension)_p
    VAL_ATTR = DatasetName
    -> Shapefile100000001 (writer SHAPEFILE_1)
    -> Table1 (writer POSTGIS_15)
    -> Table1 (writer POSTGIS_3)
    -> fastighet_y0001 (writer SDF3_1)
    -> Junction_45
    -> SchemaManipulation_9 [Feature]
SchemaManipulation_9
    DATASETNAME = @Value(DatasetName)
    Output_Gpkg_Dataset -> Table1 (writer OGCGEOPACKAGE_1)
Note: Junction_12 : Input
Junction_45
    -> Junction_46
Note: StringConcatenator_20 : Output
Junction_46
    -> Junction_12
ArcStrokerRefiner2D_9
    -> AttributeCreator_20
AttributeCreator_20
    ATTR_TABLE = SET_TO _name_extension
    -> StringConcatenator_19
StringConcatenator_19
    ACTION = Create New Attribute
    PARM_LINE = @Value(fme_feature_type)@Value(_name_extension)_y
    VAL_ATTR = DatasetName
    -> Table1 (writer POSTGIS_16)
    -> Table1 (writer POSTGIS_4)
    -> Shapefile100000002 (writer SHAPEFILE_1)
    -> fastighet_y0000 (writer SDF3_1)
    -> Junction_47
    -> SchemaManipulation_10 [Feature]
SchemaManipulation_10
    DATASETNAME = @Value(DatasetName)
    Output_Gpkg_Dataset -> Table1 (writer OGCGEOPACKAGE_1)
Note: Junction_12 : Input
Junction_47
    -> Junction_48
Note: StringConcatenator_19 : Output
Junction_48
    -> Junction_12
ArcStrokerRefiner2D_10
    -> AttributeCreator_2
AttributeCreator_2
    ATTR_TABLE = SET_TO _name_extension = _centroid
    -> StringConcatenator_21
StringConcatenator_21
    ACTION = Create New Attribute
    PARM_LINE = @Value(fme_feature_type)@Value(_name_extension)_p
    VAL_ATTR = DatasetName
    -> Shapefile100000003 (writer SHAPEFILE_1)
    -> Table1 (writer POSTGIS_16)
    -> Table1 (writer POSTGIS_4)
    -> fastighet_y000000 (writer SDF3_1)
    -> SchemaManipulation_11 [Feature]
    -> Junction_49
SchemaManipulation_11
    DATASETNAME = @Value(DatasetName)
    Output_Gpkg_Dataset -> Table1 (writer OGCGEOPACKAGE_1)
Note: Junction_12 : Input
Junction_49
    -> Junction_50
Note: StringConcatenator_21 : Output
Junction_50
    -> Junction_12
Junction_18
    -> Gemensamhetsanlaggning
Gemensamhetsanlaggning
    DATASET = @Value(Dataset)
    FME_FEATURE_TYPE_NAME = @Value(fme_feature_type_name)
    FME_FORMAT_SHORT_NAME = @Value(fme_format_short_name)
    OutSchemaFileNameSuffix = flush
    RotDirectory = ../
    _FILTERVALUE = @Value(_filterValue)
    Linje -> ArcStrokerRefiner2D_12
    Punkt -> ArcStrokerRefiner2D_11
    Yta -> ArcStrokerRefiner2D_13
    <Rejected> -> AttributeCreator_38
ArcStrokerRefiner2D_12
    -> AttributeCreator_32
AttributeCreator_32
    ATTR_TABLE:
      SET_TO fme_feature_type_name = gemensamhetsanlaggning
      SET_TO fme_feature_type = gemensamhetsanlaggning
    -> AttributeCreator_27
AttributeCreator_27
    ATTR_TABLE = SET_TO _name_extension
    -> StringConcatenator_27
StringConcatenator_27
    ACTION = Create New Attribute
    PARM_LINE = fme_basicstring:24%23%2:@Value(fme_feature_type)@Value(_name_extension)_l
    VAL_ATTR = DatasetName
    -> AttributeManager_2
ArcStrokerRefiner2D_11
    -> AttributeCreator_33
AttributeCreator_33
    ATTR_TABLE:
      SET_TO fme_feature_type_name = gemensamhetsanlaggning
      SET_TO fme_feature_type = gemensamhetsanlaggning
    -> AttributeCreator_26
AttributeCreator_26
    ATTR_TABLE = SET_TO _name_extension
    -> StringConcatenator_26
StringConcatenator_26
    ACTION = Create New Attribute
    PARM_LINE = @Value(fme_feature_type)@Value(_name_extension)_p
    VAL_ATTR = DatasetName
    -> AttributeManager_2
ArcStrokerRefiner2D_13
    -> AttributeCreator_34
AttributeCreator_34
    ATTR_TABLE:
      SET_TO fme_feature_type_name = gemensamhetsanlaggning
      SET_TO fme_feature_type = gemensamhetsanlaggning
    -> AttributeCreator_28
AttributeCreator_28
    ATTR_TABLE = SET_TO _name_extension
    -> StringConcatenator_28
StringConcatenator_28
    ACTION = Create New Attribute
    PARM_LINE = fme_basicstring:24%23%2:@Value(fme_feature_type)@Value(_name_extension)_y
    VAL_ATTR = DatasetName
    -> AttributeManager_2
AttributeManager_2
    ATTR_TABLE:
      RENAME_SET_VALUE rk_fnr > fnr
      RENAME_SET_VALUE rk_fnr_fr > fnr_fr
      RENAME_SET_VALUE rk_dep > dep
      RENAME_SET_VALUE rk_extid > extid
      RENAME_SET_VALUE rk_kommun > kommun
      RENAME_SET_VALUE rk_trakt > trakt
      RENAME_SET_VALUE rk_block_enhet > regnr
      RENAME_SET_VALUE rk_fastighet > fastighet
      REMOVE _name_extension
      REMOVE fme_feature_type_name
      REMOVE fme_feature_type
      REMOVE fme_format_short_name
      REMOVE Dataset
      REMOVE _filterValue
      REMOVE gsfnr
    -> Shapefile10000000200 (writer SHAPEFILE_1)
    -> fastighet_y00000000 (writer SDF3_1)
    -> Table1 (writer POSTGIS_7)
    -> schema (writer POSTGIS_18)
    -> Junction_51
    -> SchemaManipulation_12 [Feature]
SchemaManipulation_12
    DATASETNAME = @Value(DatasetName)
    Output_Gpkg_Dataset -> Table1 (writer OGCGEOPACKAGE_1)
Note: Junction_12 : Input
Junction_51
    -> Junction_52
Note: AttributeManager_2 : Output
Junction_52
    -> Junction_12
Junction_19
    -> Rattighet
Rattighet
    DATASET = @Value(Dataset)
    FME_FEATURE_TYPE_NAME = @Value(fme_feature_type_name)
    FME_FORMAT_SHORT_NAME = @Value(fme_format_short_name)
    OutSchemaFileNameSuffix = flush
    RotDirectory = ../
    _FILTERVALUE = @Value(_filterValue)
    Linje -> ArcStrokerRefiner2D_15
    Punkt -> ArcStrokerRefiner2D_14
    Yta -> ArcStrokerRefiner2D_16
    <Rejected> -> AttributeCreator_39
ArcStrokerRefiner2D_15
    -> AttributeCreator_35
AttributeCreator_35
    ATTR_TABLE:
      SET_TO fme_feature_type_name = rattighet
      SET_TO fme_feature_type = rattighet
    -> AttributeCreator_30
AttributeCreator_30
    ATTR_TABLE = SET_TO _name_extension
    -> StringConcatenator_30
StringConcatenator_30
    ACTION = Create New Attribute
    PARM_LINE = fme_basicstring:24%23%2:@Value(fme_feature_type)@Value(_name_extension)_l
    VAL_ATTR = DatasetName
    -> AttributeManager_3
ArcStrokerRefiner2D_14
    -> AttributeCreator_36
AttributeCreator_36
    ATTR_TABLE:
      SET_TO fme_feature_type_name = rattighet
      SET_TO fme_feature_type = rattighet
    -> AttributeCreator_29
AttributeCreator_29
    ATTR_TABLE = SET_TO _name_extension
    -> StringConcatenator_29
StringConcatenator_29
    ACTION = Create New Attribute
    PARM_LINE = @Value(fme_feature_type)@Value(_name_extension)_p
    VAL_ATTR = DatasetName
    -> AttributeManager_3
ArcStrokerRefiner2D_16
    -> AttributeCreator_37
AttributeCreator_37
    ATTR_TABLE:
      SET_TO fme_feature_type_name = rattighet
      SET_TO fme_feature_type = rattighet
    -> AttributeCreator_31
AttributeCreator_31
    ATTR_TABLE = SET_TO _name_extension
    -> StringConcatenator_31
StringConcatenator_31
    ACTION = Create New Attribute
    PARM_LINE = fme_basicstring:24%23%2:@Value(fme_feature_type)@Value(_name_extension)_y
    VAL_ATTR = DatasetName
    -> AttributeManager_3
AttributeManager_3
    ATTR_TABLE:
      REMOVE _name_extension
      REMOVE fme_feature_type_name
      REMOVE fme_feature_type
      REMOVE fme_format_short_name
      REMOVE Dataset
      REMOVE _filterValue
      REMOVE lmv_deleted
      RENAME_SET_VALUE ej_rattutredd > ej_rattutr
      RENAME_SET_VALUE sen_andr_dat > senandrdat
      RENAME_SET_VALUE rfasttillbehor > rfasttillb
      RENAME_SET_VALUE aktbet_hela > aktbet_hel
    -> Shapefile1000000020000 (writer SHAPEFILE_1)
    -> fastighet_y0000000000 (writer SDF3_1)
    -> Table1 (writer POSTGIS_8)
    -> Table1 (writer POSTGIS_19)
    -> Junction_53
    -> SchemaManipulation_13 [Feature]
SchemaManipulation_13
    DATASETNAME = @Value(DatasetName)
    Output_Gpkg_Dataset -> Table1 (writer OGCGEOPACKAGE_1)
Note: Junction_12 : Input
Junction_53
    -> Junction_54
Note: AttributeManager_3 : Output
Junction_54
    -> Junction_12
Junction_12
    -> Aggregator
Creator
    GEOMTYPE = Geometry Object
    NUM = 1
    CREATED -> ParameterFetcher_2
ParameterFetcher_2
    ATTR_LIST = ProcessName $(ProcessName) RotDirectory $(RotDirectory)
    -> UUIDGenerator_2
UUIDGenerator_2
    UUID_ATTR = ProcessID
    -> AttributeCreator_12
    -> Junction_26
AttributeCreator_12
    ATTR_TABLE = SET_TO _FeatureIdMerger = 1
    -> AttributeCreator_12_OUTPUT_-__FeatureMerger_3_SUPPLIER
    -> Junction_16
    -> Junction_20
    -> Junction_22
Junction_20
    -> Junction_21
Junction_16
    -> Junction_17
AttributeCreator_12_OUTPUT_-__FeatureMerger_3_SUPPLIER: Junction
    -> Junction
    -> Junction_3
    -> Junction_7
    -> Junction_9
    -> Junction_13
Note: FeatureMerger_2 : Supplier
Junction
    -> Junction_2
Note: FeatureMerger_3 : Supplier
Junction_3
    -> Junction_4
Note: Junction_12 : Input
Junction_13
    -> Junction_14
Note: FeatureMerger_5 : Supplier
Junction_7
    -> Junction_8
Note: FeatureMerger_6 : Supplier
Junction_9
    -> Junction_10
Junction_22
    -> Junction_23
Note: Junction_25 : Input
Junction_26
    -> Junction_25

Bookmark: SHP
Note: : [SHAPEFILE]
Note: Separeras på geometrityp för forcerande typ vid skrivande p.g.a. styrning till multipunkt. I annat fall om singel punkt är först förloras multipunkterna.
Shapefile101 (writer SHAPEFILE_1)
    attributes: source char(200), typ char(200), text char(200)
Note: : [SHAPEFILE]
Shapefile10100 (writer SHAPEFILE_1)
    attributes: source char(200), typ char(200), text char(200)
Note: : [SHAPEFILE]
Shapefile1 (writer SHAPEFILE_1)
    attributes: objid char(200), nr char(200), littera char(200), lagtillagg char(200), tillaggnr char(200), typ char(200), insamlage char(200), belstatus char(200), objstatus char(200), postnr char(200), postort char(200), namn char(200), adromr char(200), gardadromr char(200), adress char(200), gardadress char(200), nr_littera char(200)
Note: <@Value(DatasetName)>: [SHAPEFILE]
Shapefile100 (writer SHAPEFILE_1)
    attributes: td_id char(200), anvtyp char(200), anvtypform char(200), anvtypbet char(200), anvtypbesk char(200), verksam_1 char(200), apm_1 char(200), apm_1_kort char(200), apm_1_lang char(200), apm_2 char(200), apm_2_kort char(200), apm_2_lang char(200), apm_3 char(200), apm_3_kort char(200), apm_3_lang char(200), km_1 char(200), km_1_kort char(200), km_1_lang char(200), km_2 char(200), km_2_kort char(200), km_2_lang char(200), km_3 char(200), km_3_kort char(200), km_3_lang char(200), km_4 char(200), km_4_kort char(200), km_4_lang char(200), km_5 char(200), km_5_kort char(200), km_5_lang char(200),
      label_km char(254), label_apm char(254), label_alla char(254)
Note: <@Value(DatasetName)>: [SHAPEFILE]
Shapefile10001 (writer SHAPEFILE_1)
Note: <@Value(DatasetName)>: [SHAPEFILE]
Shapefile10002 (writer SHAPEFILE_1)
    attributes: typ char(200), namn_vers char(254), namn_wcap char(254), namn_icap char(254)
Note: <@Value(DatasetName)>: [SHAPEFILE]
Shapefile10000 (writer SHAPEFILE_1)
    attributes: fast_id char(200), dep char(200), fastighet char(200), trakt char(200), regnr char(200), omrade char(200), lagfart char(200), tomtrat char(200), forratt char(200), uuid char(36)
Note: <@Value(DatasetName)>: [SHAPEFILE]
Shapefile1000000 (writer SHAPEFILE_1)
    attributes: fast_id char(200), dep char(200), fastighet char(200), trakt char(200), regnr char(200), omrade char(200), lagfart char(200), tomtrat char(200), forratt char(200), l_enamn char(200), l_fnamn char(200), l_mnamn char(200), l_namn char(200), l_ponr char(200), l_tnamn char(200), t_enamn char(200), t_fnamn char(200), t_mnamn char(200), t_namn char(200), t_ponr char(200), t_tnamn char(200), tx_ponr char(200), tx_taxar char(200), uuid char(36)
Note: <@Value(DatasetName)>: [SHAPEFILE]
Note: <@Value(DatasetName)>: [SHAPEFILE]
Shapefile10000000200 (writer SHAPEFILE_1)
    attributes: fnr char(200), fnr_fr char(200), dep char(200), extid char(200), kommun char(200), trakt char(200), regnr char(200), fastighet char(200), amaltext char(254)
Note: <@Value(DatasetName)>: [SHAPEFILE]
Shapefile1000000020000 (writer SHAPEFILE_1)
    attributes: fnr char(200), dep char(200), extid char(200), gdat char(200), adat char(200), xyfel char(200), lankod char(200), aktbet char(200), rattighnr char(200), rtyp char(200), rstatus char(200), rajour char(200), ej_rattutr char(200), randamal char(200), atgard char(200), atgarddat char(200), senandrdat char(200), rperanm char(200), ranm char(200), rbesk char(254), uuid char(200), rfasttillb char(200), aktbet_hel char(254)

Bookmark: SDF
fastighet_y010000 (writer SDF3_1)
    attributes: source char(200), typ char(200), text char(200)
fastighet_y0100 (writer SDF3_1)
    attributes: objid char(200), nr char(200), littera char(200), lagtillagg char(200), tillaggnr char(200), typ char(200), insamlage char(200), belstatus char(200), objstatus char(200), postnr char(200), postort char(200), namn char(200), adromr char(200), gardadromr char(200), adress char(200), gardadress char(200), nr_littera char(200)
fastighet_y01 (writer SDF3_1)
    attributes: td_id char(200), anvtyp char(200), anvtypform char(200), anvtypbet char(200), anvtypbesk char(200), verksam_1 char(200), apm_1 char(200), apm_1_kort char(200), apm_1_lang char(200), apm_2 char(200), apm_2_kort char(200), apm_2_lang char(200), apm_3 char(200), apm_3_kort char(200), apm_3_lang char(200), km_1 char(200), km_1_kort char(200), km_1_lang char(200), km_2 char(200), km_2_kort char(200), km_2_lang char(200), km_3 char(200), km_3_kort char(200), km_3_lang char(200), km_4 char(200), km_4_kort char(200), km_4_lang char(200), km_5 char(200), km_5_kort char(200), km_5_lang char(200),
      label_km char(255), label_apm char(255), label_alla char(255)
fastighet_y0101 (writer SDF3_1)
fastighet_y0102 (writer SDF3_1)
    attributes: typ char(200), namn_vers char(255), namn_wcap char(255), namn_icap char(255)
fastighet_y (writer SDF3_1)
    attributes: fast_id char(200), dep char(200), fastighet char(200), regnr char(200), omrade char(200), trakt char(200), forratt char(200), lagfart char(200), tomtrat char(200), uuid char(36)
fastighet_lagtax_y (writer SDF3_1)
    attributes: l_enamn char(200), l_fnamn char(200), l_mnamn char(200), l_namn char(200), l_ponr char(200), l_tnamn char(200), t_enamn char(200), t_fnamn char(200), t_mnamn char(200), t_namn char(200), t_ponr char(200), t_tnamn char(200), tx_ponr char(200), tx_taxar char(200), fast_id char(200), dep char(200), fastighet char(200), regnr char(200), omrade char(200), trakt char(200), forratt char(200), lagfart char(200), tomtrat char(200), uuid char(36)
fastighet_y00000000 (writer SDF3_1)
    attributes: fnr char(200), fnr_fr char(200), dep char(200), extid char(200), kommun char(200), trakt char(200), regnr char(200), fastighet char(200), amaltext char(500)
fastighet_y0000000000 (writer SDF3_1)
    attributes: fnr char(200), dep char(200), extid char(200), gdat char(200), adat char(200), xyfel char(200), lankod char(200), aktbet char(200), rattighnr char(200), rtyp char(200), rstatus char(200), rajour char(200), ej_rattutr char(200), randamal char(200), atgard char(200), atgarddat char(200), senandrdat char(200), rperanm char(200), ranm char(200), rbesk char(500), uuid char(200), rfasttillb char(200), aktbet_hel char(255)

Bookmark: datalager@admsrv0093
Table1 (writer POSTGIS_11)
    attributes: source varchar(200), typ varchar(200), text varchar(200)
Table1 (writer POSTGIS_6)
    attributes: objid text, nr text, littera text, lagtillagg text, tillaggnr text, typ text, insamlage text, belstatus text, objstatus text, postnr text, postort text, namn text, adromr text, gardadromr text, adress text, gardadress text, nr_littera text
Table1 (writer POSTGIS_5)
    attributes: td_id varchar(200), anvtyp varchar(200), anvtypform varchar(200), anvtypbet varchar(200), anvtypbesk varchar(200), verksam_1 varchar(200), apm_1 varchar(200), apm_1_kort varchar(200), apm_1_lang varchar(200), apm_2 varchar(200), apm_2_kort varchar(200), apm_2_lang varchar(200), apm_3 text, apm_3_kort text, apm_3_lang text, km_1 text, km_1_kort text, km_1_lang text, km_2 text, km_2_kort text, km_2_lang text, km_3 text, km_3_kort text, km_3_lang text, km_4 text, km_4_kort text, km_4_lang text, km_5 text, km_5_kort text, km_5_lang text,
      label_km text, label_apm text, label_alla text
Table1 (writer POSTGIS_9)
Table1 (writer POSTGIS_10)
    attributes: typ varchar(200), namn_vers text, namn_wcap text, namn_icap text
schema (writer POSTGIS_1)
    attributes: fast_id text, dep text, fastighet text, regnr text, omrade text, trakt text, forratt text, lagfart text, tomtrat text, uuid text
Table1 (writer POSTGIS_2)
    attributes: l_enamn varchar(200), l_fnamn varchar(200), l_mnamn varchar(200), l_namn text, l_ponr text, l_tnamn text, t_enamn text, t_fnamn text, t_mnamn text, t_namn text, t_ponr text, t_tnamn text, tx_ponr text, tx_taxar text, fast_id text, dep text, fastighet text, regnr text, omrade text, trakt text, forratt text, lagfart text, tomtrat text, uuid text
Table1 (writer POSTGIS_3)
    attributes: plan_id text, planfk text, akt text, akt_egn text, akt_pb text, plannamn text, status text, statustxt text, planavgift text, tradfallej text, avvik text, avvik_dok text, d_beslut text, d_genom_f text, d_genom_t text, d_gall_t text, d_lagakra text, d_senajou text, komkod text, harpkarta text, hartkarta text, harbesk text, hargenom text, harpgbesk text, harpbest text, harkvalpro text, pav_akt text, pav_akt_n text, pav_akt_br text, pav_p_id text
Table1 (writer POSTGIS_4)
    attributes: plan_id varchar(200), planfk varchar(200), akt varchar(200), akt_egn varchar(200), akt_pb varchar(200), plannamn text, status text, statustxt text, planavgift text, tradfallej text, d_beslut text, d_genom_f text, d_genom_t text, d_gall_t text, d_lagakra text, d_senajou text, komkod text, harpkarta text, hartkarta text, harbesk text, hargenom text, harpgbesk text, harpbest text, harkvalpro text, pav_akt text, pav_p_id text
Table1 (writer POSTGIS_7)
    attributes: fnr text, fnr_fr text, dep text, extid text, kommun text, trakt text, regnr text, fastighet text, amaltext text
Table1 (writer POSTGIS_8)
    attributes: fnr text, dep text, extid text, gdat text, adat text, xyfel text, lankod text, aktbet text, rattighnr text, rtyp text, rstatus text, rajour text, ej_rattutr text, randamal text, atgard text, atgarddat text, senandrdat text, rperanm text, ranm text, rbesk text, uuid text, rfasttillb text, aktbet_hel text

Bookmark: datalager@admsrv0118
Table1 (writer POSTGIS_22)
    attributes: source varchar(200), typ varchar(200), text varchar(200)
Table1 (writer POSTGIS_17)
    attributes: objid text, nr text, littera text, lagtillagg text, tillaggnr text, typ text, insamlage text, belstatus text, objstatus text, postnr text, postort text, namn text, adromr text, gardadromr text, adress text, gardadress text, nr_littera text
Table1 (writer POSTGIS_12)
    attributes: td_id varchar(200), anvtyp varchar(200), anvtypform varchar(200), anvtypbet varchar(200), anvtypbesk varchar(200), verksam_1 varchar(200), apm_1 varchar(200), apm_1_kort varchar(200), apm_1_lang varchar(200), apm_2 varchar(200), apm_2_kort varchar(200), apm_2_lang varchar(200), apm_3 text, apm_3_kort text, apm_3_lang text, km_1 text, km_1_kort text, km_1_lang text, km_2 text, km_2_kort text, km_2_lang text, km_3 text, km_3_kort text, km_3_lang text, km_4 text, km_4_kort text, km_4_lang text, km_5 text, km_5_kort text, km_5_lang text,
      label_km text, label_apm text, label_alla text
Table1 (writer POSTGIS_20)
Table1 (writer POSTGIS_21)
    attributes: typ varchar(200), namn_vers text, namn_wcap text, namn_icap text
Table1 (writer POSTGIS_13)
    attributes: fast_id text, dep text, fastighet text, regnr text, omrade text, trakt text, lagfart text, tomtrat text, forratt text, uuid text
Table1 (writer POSTGIS_14)
    attributes: l_enamn varchar(200), l_fnamn varchar(200), l_mnamn varchar(200), l_namn text, l_ponr text, l_tnamn text, t_enamn text, t_fnamn text, t_mnamn text, t_namn text, t_ponr text, t_tnamn text, tx_ponr text, tx_taxar text, fast_id text, dep text, fastighet text, regnr text, omrade text, trakt text, lagfart text, tomtrat text, forratt text, uuid text
Table1 (writer POSTGIS_15)
    attributes: plan_id text, planfk text, akt text, akt_egn text, akt_pb text, plannamn text, status text, statustxt text, planavgift text, tradfallej text, avvik text, avvik_dok text, d_beslut text, d_genom_f text, d_genom_t text, d_gall_t text, d_lagakra text, d_senajou text, komkod text, harpkarta text, hartkarta text, harbesk text, hargenom text, harpgbesk text, harpbest text, harkvalpro text, pav_akt text, pav_akt_n text, pav_akt_br text, pav_p_id text
Table1 (writer POSTGIS_16)
    attributes: plan_id varchar(200), planfk varchar(200), akt varchar(200), akt_egn varchar(200), akt_pb varchar(200), plannamn text, status text, statustxt text, planavgift text, tradfallej text, d_beslut text, d_genom_f text, d_genom_t text, d_gall_t text, d_lagakra text, d_senajou text, komkod text, harpkarta text, hartkarta text, harbesk text, hargenom text, harpgbesk text, harpbest text, harkvalpro text, pav_akt text, pav_p_id text
schema (writer POSTGIS_18)
    attributes: fnr text, fnr_fr text, dep text, extid text, kommun text, trakt text, regnr text, fastighet text, amaltext text
Table1 (writer POSTGIS_19)
    attributes: fnr text, dep text, extid text, gdat text, adat text, xyfel text, lankod text, aktbet text, rattighnr text, rtyp text, rstatus text, rajour text, ej_rattutr text, randamal text, atgard text, atgarddat text, senandrdat text, rperanm text, ranm text, rbesk text, uuid text, rfasttillb text, aktbet_hel text

Bookmark: Loggning
TestFilter
    DEFAULT_VALUE = <UNFILTERED>
    PASSED_TEST_GROUP_OUTPUT = FIRST
    TEST_LIST = "BOOL_OP,OR,COMPOSITE_TEST,""""""1"""""",TEST_CLAUSE,TEST _reader_error ATTRIBUTE_HAS_A_VALUE """,_reader_error,"BOOL_OP,OR,COMPOSITE_TEST,""""""1"""""",TEST_CLAUSE,TEST error_msg ATTRIBUTE_HAS_A_VALUE """,error_msg,"BOOL_OP,OR,COMPOSITE_TEST,""""""1"""""",TEST_CLAUSE,TEST fme_rejection_code ATTRIBUTE_HAS_A_VALUE """,fme_rejection_code
    _reader_error -> Aggregator_6
    error_msg -> Aggregator_7
    fme_rejection_code -> Aggregator_8
Aggregator_6
    ACCUM_ATTRS_NAME = Use Attributes From One Feature
    AGGREGATE_TYPE = Homogeneous Collection (If Possible)
    GROUP_BY = _reader_error
    MODE = Geometry - Assemble One Level
    SEP = ,
    AGGREGATE -> AttributeRenamer
AttributeRenamer
    ATTR_TABLE = RENAME_SET_DEFAULT _reader_error > error_msg
    MISSING_INPUT_ATTRS = REMOVE
    -> Junction_27
Aggregator_7
    ACCUM_ATTRS_NAME = Use Attributes From One Feature
    AGGREGATE_TYPE = Homogeneous Collection (If Possible)
    GROUP_BY = error_msg
    MODE = Geometry - Assemble One Level
    SEP = ,
    AGGREGATE -> Junction_27
Aggregator_8
    ACCUM_ATTRS_NAME = Use Attributes From One Feature
    AGGREGATE_TYPE = Homogeneous Collection (If Possible)
    GROUP_BY = fme_rejection_code
    MODE = Geometry - Assemble One Level
    SEP = ,
    AGGREGATE -> AttributeRenamer_2
AttributeRenamer_2
    ATTR_TABLE = RENAME_SET_DEFAULT fme_rejection_code > error_msg
    MISSING_INPUT_ATTRS = REMOVE
    -> Junction_27
Junction_27
    -> Aggregator_9
Aggregator_9
    ACCUM_ATTRS_NAME = Use Attributes From One Feature
    AGGREGATE_TYPE = Homogeneous Collection (If Possible)
    GROUP_BY = error_msg
    MODE = Geometry - Assemble One Level
    SEP = ,
    AGGREGATE -> Aggregator_10
Aggregator_10
    ACCUM_ATTRS_NAME = Use Attributes From One Feature
    AGGREGATE_TYPE = Homogeneous Collection (If Possible)
    CONCAT_ATTRS = error_msg
    MODE = Geometry - Assemble One Level
    SEP = "\n"
    AGGREGATE -> FeatureMerger_10 [REQUESTOR]
AttributeCreator_6
    ATTR_TABLE = SET_TO _FeatureIdMerger = 1
    -> FeatureMerger_5 [REQUESTOR]
ConcatenatedSample_2
    FME_DATASET = @Value(filecopy_source_dataset)
    NumberToShorten = 3
    StringConcatenatedSample -> AttributeCreator_25
AttributeCreator_25
    ATTR_TABLE = SET_TO _FeatureIdMerger = 1
    -> FeatureMerger_7 [REQUESTOR]
AttributeCreator_22
    ATTR_TABLE = SET_TO _FeatureIdMerger = 1
    -> FeatureMerger_4 [REQUESTOR]
AttributeCreator_38
    ATTR_TABLE = SET_TO _FeatureIdMerger = 1
    -> FeatureMerger_8 [REQUESTOR]
Aggregator
    ACCUM_ATTRS_NAME = Use Attributes From One Feature
    AGGREGATE_TYPE = Homogeneous Collection (If Possible)
    COUNT_ATTR = Antal
    MODE = Geometry - Assemble One Level
    SEP = ,
    AGGREGATE -> AttributeCreator_7
AttributeCreator_7
    ATTR_TABLE = SET_TO _FeatureIdMerger = 1
    -> FeatureMerger_6 [REQUESTOR]
AttributeCreator_39
    ATTR_TABLE = SET_TO _FeatureIdMerger = 1
    -> FeatureMerger_9 [REQUESTOR]
Note: Följande kolumn förekommer fler än / en gång för specifikt dataset
Aggregator_4
    ACCUM_ATTRS_NAME = Use Attributes From One Feature
    AGGREGATE_TYPE = Homogeneous Collection (If Possible)
    COUNT_ATTR = Antal
    GROUP_BY = dl_new_column_name
    MODE = Geometry - Assemble One Level
    SEP = ", "
    AGGREGATE -> AttributeCreator_4
AttributeCreator_4
    ATTR_TABLE = SET_TO _FeatureIdMerger = 1
    -> FeatureMerger_3 [REQUESTOR]
Note: Endast till för som signal att starta logg
Sampler_2
    RATE = 1
    SAMPLE_MODE = No
    SAMPLE_TYPE_LONG = First N Features
    SAMPLED -> AttributeCreator_13
AttributeCreator_13
    ATTR_TABLE = SET_TO _FeatureIdMerger = 1
    -> FeatureMerger_2 [REQUESTOR]
Junction_21
    -> FeatureMerger_9 [SUPPLIER]
FeatureMerger_9
    ATTR_ACCUM_MODE = Merge Supplier
    ATTR_CONFLICT_RES = Use Requestor
    IGNORE_NULLS = No
    JOIN_KEYS = @Value(_FeatureIdMerger) @Value(_FeatureIdMerger) AUTO
    MERGE_TYPE = Attributes Only
    PROCESS_DUPS = NO
    REJECT_NULL_MISSING_KEYS = No
    SUPPLIERS_FIRST = No
    MERGED -> StringConcatenator_33
StringConcatenator_33
    ACTION = Create New Attribute
    PARM_LINE = fme_basicstring:37%26%21:Rättigheter kunde ej behandlas. Fel: @Value(fme_rejection_code)@Value(_reader_error)
    VAL_ATTR = Logg
    -> DTStamperYYYY-MM-DD_HH:MI:SS.sss_8
DTStamperYYYY-MM-DD_HH:MI:SS.sss_8
    -> Logg_9
Logg_9: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Junction_17
    -> FeatureMerger_7 [SUPPLIER]
FeatureMerger_7
    ATTR_ACCUM_MODE = Merge Supplier
    ATTR_CONFLICT_RES = Use Requestor
    IGNORE_NULLS = No
    JOIN_KEYS = @Value(_FeatureIdMerger) @Value(_FeatureIdMerger) AUTO
    MERGE_TYPE = Attributes Only
    PROCESS_DUPS = NO
    REJECT_NULL_MISSING_KEYS = No
    SUPPLIERS_FIRST = No
    MERGED -> StringConcatenator_25
StringConcatenator_25
    ACTION = Create New Attribute
    PARM_LINE = fme_basicstring:34%32%15%19%4:Plandokument kunde inte kopieras, @Value(fme_dataset_concatenated), totalt antal @Value(TotaltAntal) st.
    VAL_ATTR = Logg
    -> DTStamperYYYY-MM-DD_HH:MI:SS.sss_6
DTStamperYYYY-MM-DD_HH:MI:SS.sss_6
    -> Logg_7
Logg_7: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: AttributeCreator_12_-_FeatureMerger_3
Junction_2
    -> FeatureMerger_2 [SUPPLIER]
FeatureMerger_2
    ATTR_ACCUM_MODE = Merge Supplier
    ATTR_CONFLICT_RES = Use Requestor
    IGNORE_NULLS = No
    JOIN_KEYS = @Value(_FeatureIdMerger) @Value(_FeatureIdMerger) AUTO
    MERGE_TYPE = Attributes Only
    PROCESS_DUPS = NO
    REJECT_NULL_MISSING_KEYS = No
    SUPPLIERS_FIRST = No
    MERGED -> StringConcatenator_2
StringConcatenator_2
    ACTION = Create New Attribute
    PARM_LINE = Kör @Value(ProcessName) för data definierad i "$(SchemaFlush)" till datalagret.
    VAL_ATTR = Logg
    -> DTStamperYYYY-MM-DD_HH:MI:SS.sss
DTStamperYYYY-MM-DD_HH:MI:SS.sss
    -> Logg_2
Note: FeatureMerger_7 : Supplier
Note: FeatureMerger_9 : Supplier
Note: FeatureMerger_8 : Supplier
Logg_2: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,INFORMATION,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: AttributeCreator_12_-_FeatureMerger_3
Junction_4
    -> FeatureMerger_3 [SUPPLIER]
FeatureMerger_3
    ATTR_ACCUM_MODE = Merge Supplier
    ATTR_CONFLICT_RES = Use Requestor
    IGNORE_NULLS = No
    JOIN_KEYS = @Value(_FeatureIdMerger) @Value(_FeatureIdMerger) AUTO
    MERGE_TYPE = Attributes Only
    PROCESS_DUPS = NO
    REJECT_NULL_MISSING_KEYS = No
    SUPPLIERS_FIRST = No
    MERGED -> StringConcatenator_6
StringConcatenator_6
    ACTION = Create New Attribute
    PARM_LINE = Följande @Value(Antal)  st. kolumner finns det dubbletter för (@Value(dl_new_column_name)). För att exporterad data vara läsbar enligt manifest, ändra kolumnnamn i manifest.
    VAL_ATTR = Logg
    -> DTStamperYYYY-MM-DD_HH:MI:SS.sss_2
DTStamperYYYY-MM-DD_HH:MI:SS.sss_2
    -> Logg_3
Logg_3: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Junction_14
    -> FeatureMerger_4 [SUPPLIER]
FeatureMerger_4
    ATTR_ACCUM_MODE = Merge Supplier
    ATTR_CONFLICT_RES = Use Requestor
    IGNORE_NULLS = No
    JOIN_KEYS = @Value(_FeatureIdMerger) @Value(_FeatureIdMerger) AUTO
    MERGE_TYPE = Attributes Only
    PROCESS_DUPS = NO
    REJECT_NULL_MISSING_KEYS = No
    SUPPLIERS_FIRST = No
    MERGED -> StringConcatenator_3
StringConcatenator_3
    ACTION = Create New Attribute
    PARM_LINE = fme_basicstring:30%26%21:Plan kunde ej behandlas. Fel: @Value(fme_rejection_code)@Value(_reader_error)
    VAL_ATTR = Logg
    -> DTStamperYYYY-MM-DD_HH:MI:SS.sss_3
DTStamperYYYY-MM-DD_HH:MI:SS.sss_3
    -> Logg_4
Logg_4: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Junction_8
    -> FeatureMerger_5 [SUPPLIER]
FeatureMerger_5
    ATTR_ACCUM_MODE = Merge Supplier
    ATTR_CONFLICT_RES = Use Requestor
    IGNORE_NULLS = No
    JOIN_KEYS = @Value(_FeatureIdMerger) @Value(_FeatureIdMerger) AUTO
    MERGE_TYPE = Attributes Only
    PROCESS_DUPS = NO
    REJECT_NULL_MISSING_KEYS = No
    SUPPLIERS_FIRST = No
    MERGED -> StringConcatenator_7
StringConcatenator_7
    ACTION = Create New Attribute
    PARM_LINE = fme_basicstring:35%26%21:Fastighet kunde ej behandlas. Fel: @Value(fme_rejection_code)@Value(_reader_error)
    VAL_ATTR = Logg
    -> DTStamperYYYY-MM-DD_HH:MI:SS.sss_4
DTStamperYYYY-MM-DD_HH:MI:SS.sss_4
    -> Logg_6
Logg_6: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Junction_10
    -> FeatureMerger_6 [SUPPLIER]
FeatureMerger_6
    ATTR_ACCUM_MODE = Merge Supplier
    ATTR_CONFLICT_RES = Use Requestor
    IGNORE_NULLS = No
    JOIN_KEYS = @Value(_FeatureIdMerger) @Value(_FeatureIdMerger) AUTO
    MERGE_TYPE = Attributes Only
    PROCESS_DUPS = NO
    REJECT_NULL_MISSING_KEYS = No
    SUPPLIERS_FIRST = No
    MERGED -> StringConcatenator_5
StringConcatenator_5
    ACTION = Create New Attribute
    PARM_LINE = Process @Value(ProcessName) har färdigbehandlat @Value(Antal) st. objekt.
    VAL_ATTR = Logg
    -> DTStamperYYYY-MM-DD_HH:MI:SS.sss_5
DTStamperYYYY-MM-DD_HH:MI:SS.sss_5
    -> Logg_5
Logg_5: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,KLART,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Junction_23
    -> FeatureMerger_8 [SUPPLIER]
FeatureMerger_8
    ATTR_ACCUM_MODE = Merge Supplier
    ATTR_CONFLICT_RES = Use Requestor
    IGNORE_NULLS = No
    JOIN_KEYS = @Value(_FeatureIdMerger) @Value(_FeatureIdMerger) AUTO
    MERGE_TYPE = Attributes Only
    PROCESS_DUPS = NO
    REJECT_NULL_MISSING_KEYS = No
    SUPPLIERS_FIRST = No
    MERGED -> StringConcatenator_32
StringConcatenator_32
    ACTION = Create New Attribute
    PARM_LINE = fme_basicstring:50%26%21:Gemensamhetsanläggningar kunde ej behandlas. Fel: @Value(fme_rejection_code)@Value(_reader_error)
    VAL_ATTR = Logg
    -> DTStamperYYYY-MM-DD_HH:MI:SS.sss_7
DTStamperYYYY-MM-DD_HH:MI:SS.sss_7
    -> Logg_8
Logg_8: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Junction_25
    -> FeatureMerger_10 [SUPPLIER]
FeatureMerger_10
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_37
StringConcatenator_37
    ACTION = Create New Attribute
    PARM_LINE = fme_basicstring:43%26%21:Platsnamn kunde ej behandlas korrekt. Fel: @Value(fme_rejection_code)@Value(_reader_error)
    VAL_ATTR = Logg
    -> DTStamperYYYY-MM-DD_HH:MI:SS.sss_9
DTStamperYYYY-MM-DD_HH:MI:SS.sss_9
    -> Logg_10
Logg_10: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)

Bookmark: Polygon
Note: <@Value(DatasetName)>: [SHAPEFILE]
Shapefile100000000 (writer SHAPEFILE_1)
    attributes: plan_id varchar(200), planfk varchar(200), akt varchar(200), akt_egn varchar(200), akt_pb varchar(200), plannamn varchar(200), status varchar(200), statustxt varchar(200), planavgift varchar(200), tradfallej varchar(200), avvik varchar(200), avvik_dok varchar(200), d_beslut varchar(200), d_genom_f varchar(200), d_genom_t varchar(200), d_gall_t varchar(200), d_lagakra varchar(200), d_senajou varchar(200), komkod varchar(200), harpkarta varchar(200), hartkarta varchar(200), harbesk varchar(200), hargenom varchar(200), harpgbesk varchar(200), harpbest varchar(200), harkvalpro varchar(200), pav_akt varchar(254), pav_akt_n varchar(254), pav_akt_br varchar(254), pav_p_id varchar(254)
fastighet_y00 (writer SDF3_1)
    attributes: plan_id char(200), planfk char(200), akt char(200), akt_egn char(200), akt_pb char(200), plannamn char(200), status char(200), statustxt char(200), planavgift char(200), tradfallej char(200), avvik char(200), avvik_dok char(200), d_beslut char(200), d_genom_f char(200), d_genom_t char(200), d_gall_t char(200), d_lagakra char(200), d_senajou char(200), komkod char(200), harpkarta char(200), hartkarta char(200), harbesk char(200), hargenom char(200), harpgbesk char(200), harpbest char(200), harkvalpro char(200), pav_akt char(255), pav_akt_n char(255), pav_akt_br char(255), pav_p_id char(255)

Bookmark: Punkt
Note: <@Value(DatasetName)>: [SHAPEFILE]
Shapefile100000001 (writer SHAPEFILE_1)
    attributes: plan_id varchar(200), planfk varchar(200), akt varchar(200), akt_egn varchar(200), akt_pb varchar(200), plannamn varchar(200), status varchar(200), statustxt varchar(200), planavgift varchar(200), tradfallej varchar(200), avvik varchar(200), avvik_dok varchar(200), d_beslut varchar(200), d_genom_f varchar(200), d_genom_t varchar(200), d_gall_t varchar(200), d_lagakra varchar(200), d_senajou varchar(200), komkod varchar(200), harpkarta varchar(200), hartkarta varchar(200), harbesk varchar(200), hargenom varchar(200), harpgbesk varchar(200), harpbest varchar(200), harkvalpro varchar(200), pav_akt varchar(254), pav_akt_n varchar(254), pav_akt_br varchar(254), pav_p_id varchar(254)
fastighet_y0001 (writer SDF3_1)
    attributes: plan_id char(200), planfk char(200), akt char(200), akt_egn char(200), akt_pb char(200), plannamn char(200), status char(200), statustxt char(200), planavgift char(200), tradfallej char(200), avvik char(200), avvik_dok char(200), d_beslut char(200), d_genom_f char(200), d_genom_t char(200), d_gall_t char(200), d_lagakra char(200), d_senajou char(200), komkod char(200), harpkarta char(200), hartkarta char(200), harbesk char(200), hargenom char(200), harpgbesk char(200), harpbest char(200), harkvalpro char(200), pav_akt char(255), pav_akt_n char(255), pav_akt_br char(255), pav_p_id char(255)

Bookmark: Polygon
Shapefile100000002 (writer SHAPEFILE_1)
    attributes: plan_id char(200), planfk char(200), akt char(200), akt_egn char(200), plannamn char(200), status char(200), statustxt char(200), d_senajou char(200), komkod char(200)
fastighet_y0000 (writer SDF3_1)
    attributes: plan_id char(200), planfk char(200), akt char(200), akt_egn char(200), plannamn char(200), status char(200), statustxt char(200), d_senajou char(200), komkod char(200)

Bookmark: Punkt
Note: <@Value(DatasetName)>: [SHAPEFILE]
Shapefile100000003 (writer SHAPEFILE_1)
    attributes: plan_id char(200), planfk char(200), akt char(200), akt_egn char(200), plannamn char(200), status char(200), statustxt char(200), d_senajou char(200), komkod char(200)
fastighet_y000000 (writer SDF3_1)
    attributes: plan_id char(200), planfk char(200), akt char(200), akt_egn char(200), plannamn char(200), status char(200), statustxt char(200), d_senajou char(200), komkod char(200)

Bookmark: GeoPackage
Table1 (writer OGCGEOPACKAGE_1)

Bookmark: Kontrollera om kolumnnamn förekommer fler än en gång per dataset
Tester_2
    BOOL_OP = COMPOSITE
    COMPOSITE_TEST = 1 AND 2
    TEST_CLAUSE:
      TEST @Value(dl_need_new_column_name) = true
      TEST @Value(dl_new_column_name) ATTRIBUTE_HAS_VALUE ""
    TEST_MODE = TEST
    PASSED -> AttributeCreator
AttributeCreator
    ATTR_TABLE = SET_TO column_name = @Value(dl_new_column_name)
    -> Aggregator_2
Aggregator_2
    ACCUM_ATTRS_NAME = Use Attributes From One Feature
    AGGREGATE_TYPE = Homogeneous Collection (If Possible)
    COUNT_ATTR = AntalSameColumns
    GROUP_BY = fme_feature_type_name dl_new_column_name
    MODE = Geometry - Assemble One Level
    SEP = ,
    AGGREGATE -> Tester_3
Tester_3
    BOOL_OP = OR
    TEST_CLAUSE = TEST @Value(AntalSameColumns) > 1
    TEST_MODE = TEST
    PASSED -> Aggregator_4

FME custom transformer Detaljplanemosaik_användning

Parameters:
- RotDirectory = ../   # Katalogen där processen startar
- ProcessModulName =   # Processmodulsnamn
- OutSchemaFileNameSuffix = flush   # Suffix på filnamn för schemalistning (skapas med bindestreck)
- _FILTERVALUE = @Value(_filterValue)   # Filtervalue
- DATASET = @Value(Dataset)   # Dataset
- FME_FEATURE_TYPE_NAME = @Value(fme_feature_type_name)   # Fme Feature Type Name
- FME_FORMAT_SHORT_NAME = @Value(fme_format_short_name)   # Fme Format Short Name

Input (input)
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(_filterValue) = td_detaljplan.dp_anvandningbest_y",td_detaljplan.dp_anvandningbest_y,"BOOL_OP,OR,COMPOSITE_TEST,""""""1"""""",TEST_CLAUSE,TEST @Value(_filterValue) = td_detaljplan.dp_dt_anvandningtyp",td_detaljplan.dp_dt_anvandningtyp,"BOOL_OP,OR,COMPOSITE_TEST,""""""1"""""",TEST_CLAUSE,TEST @Value(_filterValue) = td_detaljplan.td_an_dt_verksamhet_1",td_detaljplan.td_an_dt_verksamhet_1,"BOOL_OP,OR,COMPOSITE_TEST,""""""1"""""",TEST_CLAUSE,TEST @Value(_filterValue) = td_detaljplan.eg_dt_anvandning_allman_platsmark",td_detaljplan.eg_dt_anvandning_allman_platsmark,"BOOL_OP,OR,COMPOSITE_TEST,""""""1"""""",TEST_CLAUSE,TEST @Value(_filterValue) = td_detaljplan.eg_dt_anvandning_kvartersmark",td_detaljplan.eg_dt_anvandning_kvartersmark
    td_detaljplan.dp_anvandningbest_y -> FeatureReader_4 [INITIATOR]
    td_detaljplan.dp_dt_anvandningtyp -> FeatureReader_5 [INITIATOR]
    td_detaljplan.td_an_dt_verksamhet_1 -> FeatureReader_6 [INITIATOR]
    td_detaljplan.eg_dt_anvandning_allman_platsmark -> FeatureReader_2 [INITIATOR]
    td_detaljplan.eg_dt_anvandning_kvartersmark -> FeatureReader_3 [INITIATOR]
    <UNFILTERED> -> Junction
FeatureReader_4
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer
AttributeExposer
    ATTR_LIST = td_id,dp_anvandningtyp,td_dp_verksamhet_1,ex_anv_apm_01,ex_anv_apm_02,ex_anv_apm_03,ex_anv_km_01,ex_anv_km_02,ex_anv_km_03,ex_anv_km_04,ex_anv_km_05
    -> BulkAttributeRenamer
BulkAttributeRenamer
    ATTRCHOICE = All Attributes
    MODE_CHOICE = RENAME
    PATTERN_ACTION_DISP = ADDPREFIX
    REPLACE_STR = f_
    -> FeatureMerger [REQUESTOR]
Note: <Rejected>
Junction
    -> Junction_2
Note: TestFilter_2 : <Unfiltered>
Junction_2
    -> <Rejected> (output)
FeatureReader_5
    ATTR_ACCUM_MODE = Only Use Result
    COMBINE_GEOM = Use Result
    DATASET = @Value(Dataset)
    FEATURETYPES = @Value(fme_feature_type_name)
    FORMAT = POSTGRES
    OUTPUT_FEATURES_DISPLAY = Schema and Data Features
    POSTGRES_CREATE_FEATURE_TABLES_FROM_DATA = Yes
    POSTGRES_FEATURES_PER_FETCH = 10000
    POSTGRES_NAMED_CONNECTION = @Value(Dataset)
    POSTGRES_QUERY_FEATURE_TYPES_FOR_MERGE_FILTERS = Yes
    POSTGRES_READ_TIME_WITH_TIMEZONE = Yes
    <OTHER> -> AttributeExposer_2
AttributeExposer_2
    ATTR_LIST = dp_anvandningtyp,td_anv_form,td_beteckning,td_beskrivning
    -> BulkAttributeRenamer_2
BulkAttributeRenamer_2
    ATTRCHOICE = All Attributes
    MODE_CHOICE = RENAME
    PATTERN_ACTION_DISP = ADDPREFIX
    REPLACE_STR = anv_typ_
    -> FeatureMerger [SUPPLIER]
FeatureMerger
    ATTR_ACCUM_MODE = Merge Supplier
    ATTR_CONFLICT_RES = Use Requestor
    IGNORE_NULLS = No
    JOIN_KEYS = @Value(f_dp_anvandningtyp) @Value(anv_typ_dp_anvandningtyp) AUTO
    MERGE_TYPE = Attributes Only
    PROCESS_DUPS = NO
    REJECT_NULL_MISSING_KEYS = No
    SUPPLIERS_FIRST = No
    MERGED -> Junction_3
    UNMERGED_REQUESTOR -> Junction_3
    <REJECTED> -> Junction_9
Junction_3
    -> FeatureMerger_2 [REQUESTOR]
Note: <Rejected>
Junction_9
    -> Junction_10
Note: FeatureMerger : <Rejected>
Junction_10
    -> <Rejected> (output)
FeatureReader_6
    ATTR_ACCUM_MODE = Only Use Result
    COMBINE_GEOM = Use Result
    DATASET = @Value(Dataset)
    FEATURETYPES = @Value(fme_feature_type_name)
    FORMAT = POSTGRES
    OUTPUT_FEATURES_DISPLAY = Schema and Data Features
    POSTGRES_CREATE_FEATURE_TABLES_FROM_DATA = Yes
    POSTGRES_FEATURES_PER_FETCH = 10000
    POSTGRES_NAMED_CONNECTION = @Value(Dataset)
    POSTGRES_QUERY_FEATURE_TYPES_FOR_MERGE_FILTERS = Yes
    POSTGRES_READ_TIME_WITH_TIMEZONE = Yes
    <OTHER> -> AttributeExposer_3
AttributeExposer_3
    ATTR_LIST = td_dp_verksamhet_1
    -> BulkAttributeRenamer_3
BulkAttributeRenamer_3
    ATTRCHOICE = All Attributes
    MODE_CHOICE = RENAME
    PATTERN_ACTION_DISP = ADDPREFIX
    REPLACE_STR = verk_1_
    -> FeatureMerger_2 [SUPPLIER]
FeatureMerger_2
    ATTR_ACCUM_MODE = Merge Supplier
    ATTR_CONFLICT_RES = Use Requestor
    IGNORE_NULLS = No
    JOIN_KEYS = @Value(f_td_dp_verksamhet_1) @Value(verk_1_td_dp_verksamhet_1) AUTO
    MERGE_TYPE = Attributes Only
    PROCESS_DUPS = NO
    REJECT_NULL_MISSING_KEYS = No
    SUPPLIERS_FIRST = No
    MERGED -> Junction_4
    UNMERGED_REQUESTOR -> Junction_4
    <REJECTED> -> Junction_11
Junction_4
    -> FeatureMerger_3 [REQUESTOR]
Note: <Rejected>
Junction_11
    -> Junction_12
Note: FeatureMerger_2 : <Rejected>
Junction_12
    -> <Rejected> (output)
Note: FeatureMerger_3 : <Rejected>
Junction_14
    -> <Rejected> (output)
Note: FeatureMerger_5 : <Rejected>
Junction_18
    -> <Rejected> (output)
Note: FeatureMerger_4 : <Rejected>
Junction_16
    -> <Rejected> (output)
FeatureReader_3
    ATTR_ACCUM_MODE = Only Use Result
    COMBINE_GEOM = Use Result
    DATASET = @Value(Dataset)
    FEATURETYPES = @Value(fme_feature_type_name)
    FORMAT = POSTGRES
    OUTPUT_FEATURES_DISPLAY = Schema and Data Features
    POSTGRES_CREATE_FEATURE_TABLES_FROM_DATA = Yes
    POSTGRES_FEATURES_PER_FETCH = 10000
    POSTGRES_NAMED_CONNECTION = @Value(Dataset)
    POSTGRES_QUERY_FEATURE_TYPES_FOR_MERGE_FILTERS = Yes
    POSTGRES_READ_TIME_WITH_TIMEZONE = Yes
    <OTHER> -> AttributeExposer_5
AttributeExposer_5
    ATTR_LIST = anvandning_id,td_beskrivning_kort,td_beskrivning_lang
    -> BulkAttributeRenamer_5
BulkAttributeRenamer_5
    ATTRCHOICE = All Attributes
    MODE_CHOICE = RENAME
    PATTERN_ACTION_DISP = ADDPREFIX
    REPLACE_STR = km_
    -> FeatureMerger_6 [SUPPLIER]
    -> Junction_20
FeatureMerger_6
    ATTR_ACCUM_MODE = Prefix Supplier
    IGNORE_NULLS = No
    JOIN_KEYS = @Value(f_ex_anv_km_01) @Value(km_anvandning_id) AUTO
    MERGE_TYPE = Attributes Only
    PROCESS_DUPS = NO
    REJECT_NULL_MISSING_KEYS = No
    SUPPLIERS_FIRST = No
    SUPPLIER_PREFIX = 1_
    MERGED -> Junction_19
    UNMERGED_REQUESTOR -> Junction_19
    <REJECTED> -> Junction_24
Junction_19
    -> FeatureMerger_7 [REQUESTOR]
Note: <Rejected>
Junction_24
    -> Junction_25
Note: FeatureMerger_6 : <Rejected>
Junction_25
    -> <Rejected> (output)
Junction_20
    -> FeatureMerger_7 [SUPPLIER]
    -> FeatureMerger_8 [SUPPLIER]
    -> FeatureMerger_9 [SUPPLIER]
    -> FeatureMerger_10 [SUPPLIER]
FeatureMerger_7
    ATTR_ACCUM_MODE = Prefix Supplier
    IGNORE_NULLS = No
    JOIN_KEYS = @Value(f_ex_anv_km_02) @Value(km_anvandning_id) AUTO
    MERGE_TYPE = Attributes Only
    PROCESS_DUPS = NO
    REJECT_NULL_MISSING_KEYS = No
    SUPPLIERS_FIRST = No
    SUPPLIER_PREFIX = 2_
    MERGED -> Junction_21
    UNMERGED_REQUESTOR -> Junction_21
    <REJECTED> -> Junction_26
Junction_21
    -> FeatureMerger_8 [REQUESTOR]
FeatureMerger_8
    ATTR_ACCUM_MODE = Prefix Supplier
    IGNORE_NULLS = No
    JOIN_KEYS = @Value(f_ex_anv_km_03) @Value(km_anvandning_id) AUTO
    MERGE_TYPE = Attributes Only
    PROCESS_DUPS = NO
    REJECT_NULL_MISSING_KEYS = No
    SUPPLIERS_FIRST = No
    SUPPLIER_PREFIX = 3_
    MERGED -> Junction_22
    UNMERGED_REQUESTOR -> Junction_22
    <REJECTED> -> Junction_28
Junction_22
    -> FeatureMerger_9 [REQUESTOR]
FeatureMerger_9
    ATTR_ACCUM_MODE = Prefix Supplier
    IGNORE_NULLS = No
    JOIN_KEYS = @Value(f_ex_anv_km_04) @Value(km_anvandning_id) AUTO
    MERGE_TYPE = Attributes Only
    PROCESS_DUPS = NO
    REJECT_NULL_MISSING_KEYS = No
    SUPPLIERS_FIRST = No
    SUPPLIER_PREFIX = 4_
    MERGED -> Junction_23
    UNMERGED_REQUESTOR -> Junction_23
    <REJECTED> -> Junction_30
Junction_23
    -> FeatureMerger_10 [REQUESTOR]
FeatureMerger_10
    ATTR_ACCUM_MODE = Prefix Supplier
    IGNORE_NULLS = No
    JOIN_KEYS = @Value(f_ex_anv_km_05) @Value(km_anvandning_id) AUTO
    MERGE_TYPE = Attributes Only
    PROCESS_DUPS = NO
    REJECT_NULL_MISSING_KEYS = No
    SUPPLIERS_FIRST = No
    SUPPLIER_PREFIX = 5_
    MERGED -> AttributeExposer_6
    UNMERGED_REQUESTOR -> AttributeExposer_6
    <REJECTED> -> Junction_32
AttributeExposer_6
    ATTR_LIST = fme_feature_type_name,fme_feature_type
    -> AttributeManager
AttributeManager
    ATTR_TABLE:
      RENAME_SET_VALUE f_td_id > td_id
      RENAME_SET_VALUE f_dp_anvandningtyp > anvtyp
      RENAME_SET_VALUE anv_typ_td_anv_form > anvtypform
      RENAME_SET_VALUE anv_typ_td_beteckning > anvtypbet
      RENAME_SET_VALUE anv_typ_td_beskrivning > anvtypbesk
      RENAME_SET_VALUE f_td_dp_verksamhet_1 > verksam_1
      RENAME_SET_VALUE f_ex_anv_apm_01 > apm_1
      RENAME_SET_VALUE 1_apm_td_beskrivning_kort > apm_1_kort
      RENAME_SET_VALUE 1_apm_td_beskrivning_lang > apm_1_lang
      RENAME_SET_VALUE f_ex_anv_apm_02 > apm_2
      RENAME_SET_VALUE 2_apm_td_beskrivning_kort > apm_2_kort
      RENAME_SET_VALUE 2_apm_td_beskrivning_lang > apm_2_lang
      RENAME_SET_VALUE f_ex_anv_apm_03 > apm_3
      RENAME_SET_VALUE 3_apm_td_beskrivning_kort > apm_3_kort
      RENAME_SET_VALUE 3_apm_td_beskrivning_lang > apm_3_lang
      RENAME_SET_VALUE f_ex_anv_km_01 > km_1
      RENAME_SET_VALUE 1_km_td_beskrivning_kort > km_1_kort
      RENAME_SET_VALUE 1_km_td_beskrivning_lang > km_1_lang
      RENAME_SET_VALUE f_ex_anv_km_02 > km_2
      RENAME_SET_VALUE 2_km_td_beskrivning_kort > km_2_kort
      RENAME_SET_VALUE 2_km_td_beskrivning_lang > km_2_lang
      RENAME_SET_VALUE f_ex_anv_km_03 > km_3
      RENAME_SET_VALUE 3_km_td_beskrivning_kort > km_3_kort
      RENAME_SET_VALUE 3_km_td_beskrivning_lang > km_3_lang
      RENAME_SET_VALUE f_ex_anv_km_04 > km_4
      RENAME_SET_VALUE 4_km_td_beskrivning_kort > km_4_kort
      RENAME_SET_VALUE 4_km_td_beskrivning_lang > km_4_lang
      RENAME_SET_VALUE f_ex_anv_km_05 > km_5
      RENAME_SET_VALUE 5_km_td_beskrivning_kort > km_5_kort
      RENAME_SET_VALUE 5_km_td_beskrivning_lang > km_5_lang
      REMOVE anv_typ_dp_anvandningtyp
      REMOVE verk_1_td_dp_verksamhet_1
      REMOVE 1_apm_anvandning_id
      REMOVE 2_apm_anvandning_id
      REMOVE 3_apm_anvandning_id
      REMOVE 1_km_anvandning_id
      REMOVE 2_km_anvandning_id
      REMOVE 3_km_anvandning_id
      REMOVE 4_km_anvandning_id
      REMOVE 5_km_anvandning_id
      SET_TO fme_feature_type_name = dp_anvandningbest
      SET_TO fme_feature_type = dp_anvandningbest
    -> StringConcatenator_2
StringConcatenator_2
    ACTION = Create New Attribute
    PARM_LINE = fme_basicstring:17%17%17%17%17:@Value(km_1_kort)@Value(km_2_kort)@Value(km_3_kort)@Value(km_4_kort)@Value(km_5_kort)
    VAL_ATTR = label_km
    -> StringConcatenator
StringConcatenator
    ACTION = Create New Attribute
    PARM_LINE = fme_basicstring:18%1%18%1%18:@Value(apm_1_kort) @Value(apm_2_kort) @Value(apm_3_kort)
    VAL_ATTR = label_apm
    -> AttributeTrimmer
AttributeTrimmer
    SRC_ATTRS = label_apm,label_km
    TRIM_CHARS = " "
    TRIM_TO_NONE = Yes
    TRIM_TYPE = Both
    -> StringConcatenator_3
StringConcatenator_3
    ACTION = Create New Attribute
    PARM_LINE = fme_basicstring:16%1%17:@Value(label_km) @Value(label_apm)
    VAL_ATTR = label_alla
    -> AttributeTrimmer_2
AttributeTrimmer_2
    SRC_ATTRS = label_alla
    TRIM_CHARS = " "
    TRIM_TO_NONE = Yes
    TRIM_TYPE = Both
    -> Output (output)
Output (output)
Note: <Rejected>
Junction_32
    -> Junction_33
Note: FeatureMerger_10 : <Rejected>
Junction_33
    -> <Rejected> (output)
Note: <Rejected>
Junction_30
    -> Junction_31
Note: FeatureMerger_9 : <Rejected>
Junction_31
    -> <Rejected> (output)
Note: <Rejected>
Junction_28
    -> Junction_29
Note: FeatureMerger_8 : <Rejected>
Junction_29
    -> <Rejected> (output)
Note: <Rejected>
Junction_26
    -> Junction_27
Note: FeatureMerger_7 : <Rejected>
Junction_27
    -> <Rejected> (output)
<Rejected> (output)

Bookmark: Allmän platsmark
FeatureReader_2
    ATTR_ACCUM_MODE = Only Use Result
    COMBINE_GEOM = Use Result
    DATASET = @Value(Dataset)
    FEATURETYPES = @Value(fme_feature_type_name)
    FORMAT = POSTGRES
    OUTPUT_FEATURES_DISPLAY = Schema and Data Features
    POSTGRES_CREATE_FEATURE_TABLES_FROM_DATA = Yes
    POSTGRES_FEATURES_PER_FETCH = 10000
    POSTGRES_NAMED_CONNECTION = @Value(Dataset)
    POSTGRES_QUERY_FEATURE_TYPES_FOR_MERGE_FILTERS = Yes
    POSTGRES_READ_TIME_WITH_TIMEZONE = Yes
    <OTHER> -> AttributeExposer_4
AttributeExposer_4
    ATTR_LIST = anvandning_id,td_beskrivning_kort,td_beskrivning_lang
    -> BulkAttributeRenamer_4
BulkAttributeRenamer_4
    ATTRCHOICE = All Attributes
    MODE_CHOICE = RENAME
    PATTERN_ACTION_DISP = ADDPREFIX
    REPLACE_STR = apm_
    -> FeatureMerger_3 [SUPPLIER]
    -> Junction_6
FeatureMerger_3
    ATTR_ACCUM_MODE = Prefix Supplier
    IGNORE_NULLS = No
    JOIN_KEYS = @Value(f_ex_anv_apm_01) @Value(apm_anvandning_id) AUTO
    MERGE_TYPE = Attributes Only
    PROCESS_DUPS = NO
    REJECT_NULL_MISSING_KEYS = No
    SUPPLIERS_FIRST = No
    SUPPLIER_PREFIX = 1_
    MERGED -> Junction_5
    UNMERGED_REQUESTOR -> Junction_5
    <REJECTED> -> Junction_13
Junction_5
    -> FeatureMerger_4 [REQUESTOR]
Note: <Rejected>
Junction_13
    -> Junction_14
Junction_6
    -> FeatureMerger_4 [SUPPLIER]
    -> FeatureMerger_5 [SUPPLIER]
FeatureMerger_4
    ATTR_ACCUM_MODE = Prefix Supplier
    IGNORE_NULLS = No
    JOIN_KEYS = @Value(f_ex_anv_apm_02) @Value(apm_anvandning_id) AUTO
    MERGE_TYPE = Attributes Only
    PROCESS_DUPS = NO
    REJECT_NULL_MISSING_KEYS = No
    SUPPLIERS_FIRST = No
    SUPPLIER_PREFIX = 2_
    MERGED -> Junction_7
    UNMERGED_REQUESTOR -> Junction_7
    <REJECTED> -> Junction_15
Junction_7
    -> FeatureMerger_5 [REQUESTOR]
FeatureMerger_5
    ATTR_ACCUM_MODE = Prefix Supplier
    IGNORE_NULLS = No
    JOIN_KEYS = @Value(f_ex_anv_apm_03) @Value(apm_anvandning_id) AUTO
    MERGE_TYPE = Attributes Only
    PROCESS_DUPS = NO
    REJECT_NULL_MISSING_KEYS = No
    SUPPLIERS_FIRST = No
    SUPPLIER_PREFIX = 3_
    MERGED -> Junction_8
    UNMERGED_REQUESTOR -> Junction_8
    <REJECTED> -> Junction_17
Junction_8
    -> FeatureMerger_6 [REQUESTOR]
Note: <Rejected>
Junction_17
    -> Junction_18
Note: <Rejected>
Junction_15
    -> Junction_16

FME custom transformer SchemaManipulation

Parameters:
- DATASETNAME = @Value(DatasetName)   # DatasetName

Feature (input)
    -> AttributeCreator_44
Note: Unmerged för att få med dataseten som saknar attribut helt.
FeatureMerger
    ATTR_ACCUM_MODE = Merge Supplier
    ATTR_CONFLICT_RES = Use Requestor
    IGNORE_NULLS = No
    JOIN_KEYS = @Value(DatasetName) @Value(fme_feature_type_name) AUTO
    MERGE_TYPE = Attributes Only
    PROCESS_DUPS = NO
    REJECT_NULL_MISSING_KEYS = No
    SUPPLIERS_FIRST = No
    MERGED -> AttributeExposer_4
    UNMERGED_REQUESTOR -> AttributeExposer_4
Output_General_Dataset (output)
Output_Gpkg_Dataset (output)

Bookmark: Schema-manipulering
Note: Strikt schema för att inte få med exv. DatasetName och fme-attribut i datasetet.
AttributeCreator_44
    ATTR_TABLE = SET_TO fme_feature_type_name = @Value(DatasetName)
    -> SchemaScanner
SchemaScanner
    CASE = No
    EMPTY_ATTR_HANDLING = SCANNER_DEFAULT
    GROUP_BY = DatasetName
    HOLD = Yes
    SCHEMA_NAME_ATTR = DatasetName
    UNBOUNDED_NUMBERS = Yes
    UNBOUNDED_STRINGS = No
    -> FeatureMerger [REQUESTOR]
    <SCHEMA> -> ListExploder
ListExploder
    ATTR_ACCUM_MODE = Merge List Attributes
    ATTR_CONFLICT_RES = Use List Attribute Values
    INDEX_ATTR = _element_index
    LIST_ATTR = attribute{}
    ELEMENTS -> Tester_5
Note: Behöver uppdateras när systemattribut inte ska skrivas till utdata
Note: Tester_5 [Tester] / Test Clauses: LogicLeft ValueOperatorRight ValueMode@Value(name)=DatasetNameAutomaticOR@Value(name)=_name_extensionAutomaticOR@Value(name)Begins Withfme_Case InsensitiveOR@Value(name)Contains_fme_Case InsensitiveAdvanced: / Preserve Feature Order: Per Output Port
Tester_5
    BOOL_OP = OR
    TEST_CLAUSE:
      TEST @Value(name) = DatasetName
      TEST @Value(name) = _name_extension
      CASE_INSENSITIVE_TEST @Value(name) BEGINS_WITH fme_
      CASE_INSENSITIVE_TEST @Value(name) CONTAINS _fme_
    TEST_MODE = PER_TEST
    FAILED -> Aggregator_11
Aggregator_11
    ACCUM_ATTRS_NAME = Drop Incoming Attributes
    AGGREGATE_TYPE = Homogeneous Collection (If Possible)
    GROUP_BY = fme_feature_type_name
    LIST_NAME = attribute
    MODE = Geometry - Assemble One Level
    SEP = ,
    AGGREGATE -> FeatureMerger [SUPPLIER]

Bookmark: New Bookmark
AttributeExposer_4
    ATTR_LIST = fme_schema_handling,fme_type,attribute{}
    -> AttributeRemover_3
AttributeRemover_3
    REMOVE_ATTRS = fme_schema_handling
    -> AttributeCreator_45
Note: Plockar bort fme_schema_handling som annars gör så att 1:a featuren inte skrivs. / fme_geometry{0} behöver ha värde för att skrivaren ska veta vilken typ a geometri. Är tom i detta fall och behöver därför sättas genom fme_type.
AttributeCreator_45
    ATTR_TABLE = SET_TO fme_geometry{0} = @Value(fme_type)
    -> Counter
    -> Output_General_Dataset (output)

Bookmark: Skapa godtycklig primärnyckel åt GeoPackage
Counter
    CNT_ATTR = gpkg_id
    GROUP_BY = DatasetName
    SCOPE = Local
    START = 1
    -> AttributeCreator_42
AttributeCreator_42
    ATTR_TABLE:
      SET_TO name = gpkg_id
      SET_TO fme_data_type = fme_int64,PrimaryKey
    -> ListElementCounter
ListElementCounter
    CNT_ATTR = _attribute_element_count
    LIST_NAME = attribute{}
    -> AttributeCreator_43
AttributeCreator_43
    ATTR_TABLE:
      SET_TO attribute{@Value(_attribute_element_count)}.name = @Value(name)
      SET_TO attribute{@Value(_attribute_element_count)}.fme_data_type = @Value(fme_data_type)
    -> AttributeRemover_2
AttributeRemover_2
    REMOVE_ATTRS = fme_data_type,name
    -> Output_Gpkg_Dataset (output)

FME custom transformer Search

Parameters:
- RotDirectory = ../   # Katalogen där processen startar
- ProcessModulName =   # Processmodulsnamn
- OutSchemaFileNameSuffix = flush   # Suffix på filnamn för schemalistning (skapas med bindestreck)
- _FILTERVALUE = @Value(_filterValue)   # Filtervalue
- DATASET = @Value(Dataset)   # Dataset
- FME_FEATURE_TYPE_NAME = @Value(fme_feature_type_name)   # Fme Feature Type Name

Input (input)
    -> AttributeExposer_8
AttributeExposer_8
    ATTR_LIST = fme_feature_type
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(_filterValue) = ex_special.eg_omrade_y",ex_special.eg_omrade_y,"BOOL_OP,OR,COMPOSITE_TEST,""""""1"""""",TEST_CLAUSE,TEST @Value(fme_feature_type) = td_bal.bal_adressplats_p",td_bal.bal_adressplats_p,"BOOL_OP,OR,COMPOSITE_TEST,""""""1"""""",TEST_CLAUSE,TEST @Value(_filterValue) = td_bal.bal_byggnad_y",td_bal.bal_byggnad_y,"BOOL_OP,OR,COMPOSITE_TEST,""""""1"""""",TEST_CLAUSE,TEST @Value(_filterValue) = td_baskarta.ma_markanvandningyta_y",td_baskarta.ma_markanvandningyta_y,"BOOL_OP,OR,COMPOSITE_TEST,""""""1"""""",TEST_CLAUSE,TEST @Value(_filterValue) = td_baskarta.md_markdetalj_l",td_baskarta.md_markdetalj_l,"BOOL_OP,OR,COMPOSITE_TEST,""""""1"""""",TEST_CLAUSE,TEST @Value(_filterValue) = td_baskarta.md_markdetalj_y",td_baskarta.md_markdetalj_y,"BOOL_OP,OR,COMPOSITE_TEST,""""""1"""""",TEST_CLAUSE,TEST @Value(_filterValue) = td_baskarta.mt_marktackeyta_y",td_baskarta.mt_marktackeyta_y,"BOOL_OP,OR,COMPOSITE_TEST,""""""1"""""",TEST_CLAUSE,TEST @Value(_filterValue) = td_baskarta.td_namn_p",td_baskarta.td_namn_p
    ex_special.eg_omrade_y -> FeatureReader_4 [INITIATOR]
    td_bal.bal_adressplats_p -> AttributeExposer
    td_bal.bal_byggnad_y -> FeatureReader_2 [INITIATOR]
    td_baskarta.ma_markanvandningyta_y -> FeatureReader_3 [INITIATOR]
    td_baskarta.md_markdetalj_l -> FeatureReader_6 [INITIATOR]
    td_baskarta.md_markdetalj_y -> FeatureReader_5 [INITIATOR]
    td_baskarta.mt_marktackeyta_y -> FeatureReader_7 [INITIATOR]
    td_baskarta.td_namn_p -> FeatureReader_8 [INITIATOR]
Note: AttributeCreator_7 [AttributeCreator] / Attributes To Create: New AttributeAttribute Value_name_extension_search_y
AttributeCreator_7
    ATTR_TABLE = SET_TO _name_extension = _search_y
    -> GeometryFilter
ThickenThinPolygon_2
    Buffer = 1
    IsRectangle = NO
    -> AttributeCreator_4
    <Rejected> -> <Rejected> (output)
Note: AttributeCreator_2 [AttributeCreator] / Attributes To Create: New AttributeAttribute Value_name_extension_search_bb_y
AttributeCreator_2
    ATTR_TABLE = SET_TO _name_extension = _search_bb_y
    -> ThickenThinPolygon
ThickenThinPolygon
    Buffer = 1
    IsRectangle = YES
    -> AttributeCreator_4
    <Rejected> -> <Rejected> (output)
<Rejected> (output)
Note: AttributeCreator_3 [AttributeCreator] / Attributes To Create: New AttributeAttribute Value_name_extension_search_mp
AttributeCreator_3
    ATTR_TABLE = SET_TO _name_extension = _search_mp
    -> AttributeCreator_4
Note: AttributeCreator_4 [AttributeCreator] / Attributes To Create: New AttributeAttribute Value_nameplatsnamn
AttributeCreator_4
    ATTR_TABLE = SET_TO _name = platsnamn
    -> Output (output)
Output (output)

Bookmark: stadsdel
FeatureReader_4
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_3
    <REJECTED> -> <Rejected> (output)
AttributeExposer_3
    ATTR_LIST = omradestyp,namn
    -> Tester_6
Tester_6
    BOOL_OP = OR
    TEST_CLAUSE = TEST @Value(omradestyp) = stadsdel
    TEST_MODE = TEST
    PASSED -> StringCaseChanger_3
StringCaseChanger_3
    ATTRCHOICE = Selected Attributes
    ATTRLIST = omradestyp
    CHANGE_TYPE = lowercase
    -> StringCaseChanger_2
StringCaseChanger_2
    ATTRCHOICE = Selected Attributes
    ATTRLIST = namn
    CHANGE_TYPE = Title case
    -> AttributeManager_4
Note: AttributeManager_4 [AttributeManager] / Attribute Actions: Input AttributeOutput AttributeAttribute ValueActionsourceex_special.eg_omrade_ySet ValueomradestyptypRenamenamntextRename
AttributeManager_4
    ATTR_TABLE:
      SET_TO source = ex_special.eg_omrade_y
      RENAME_SET_VALUE omradestyp > typ
      RENAME_SET_VALUE namn > text
    -> SearchBoundingBoxAndPoint
    -> AttributeCreator_7
SearchBoundingBoxAndPoint
    ATTRIBUTES = source text typ
    RotDirectory = ../
    BoundingBox -> AttributeCreator_2
    point -> AttributeCreator_3
    <Rejected> -> <Rejected> (output)

Bookmark: populärnamn adress
AttributeExposer
    ATTR_LIST = bal_nummer,bal_bokstavstillagg,bal_typ,td_adressomradesnamn,td_gardsadressomradesnamn,bal_belagenhetsstatus,bal_namn
    -> Tester_12
Tester_12
    BOOL_OP = OR
    TEST_CLAUSE = TEST @Value(bal_belagenhetsstatus) = Gällande
    TEST_MODE = TEST
    PASSED -> AttributeKeeper_6
    PASSED -> AttributeKeeper_5
AttributeKeeper_5
    CREATE_BULK_MODE_FEATURES = NO
    KEEP_ATTRS = bal_namn
    -> Tester_5
Tester_5
    BOOL_OP = OR
    TEST_CLAUSE = TEST bal_namn ATTRIBUTE_HAS_A_VALUE ""
    TEST_MODE = TEST
    PASSED -> AttributeManager_5
Note: AttributeManager_5 [AttributeManager] / Attribute Actions: Input AttributeOutput AttributeAttribute ValueActionsourcetd_bal.bal_adressplats_pSet Valuetyppopulärnamn adressSet Valuebal_namntextRename
AttributeManager_5
    ATTR_TABLE:
      SET_TO source = td_bal.bal_adressplats_p
      SET_TO typ = populärnamn adress
      RENAME_SET_VALUE bal_namn > text
    -> StringCaseChanger_4
StringCaseChanger_4
    ATTRCHOICE = Selected Attributes
    ATTRLIST = typ
    CHANGE_TYPE = lowercase
    -> SearchBoundingBoxAndPoint_2
SearchBoundingBoxAndPoint_2
    ATTRIBUTES = source text typ
    RotDirectory = ../
    BoundingBox -> AttributeCreator_2
    BoundingBox -> AttributeCreator_7
    point -> AttributeCreator_3
    <Rejected> -> <Rejected> (output)

Bookmark: adressområde, schablon
AttributeKeeper_6
    CREATE_BULK_MODE_FEATURES = NO
    KEEP_ATTRS = bal_bokstavstillagg,bal_nummer,bal_typ,td_adressomradesnamn,td_gardsadressomradesnamn
    -> Sorter
Sorter
    SORT_PARM = td_adressomradesnamn ALPHA ASCENDING bal_nummer NUMERIC ASCENDING bal_bokstavstillagg ALPHA ASCENDING
    SORTED -> AttributeRenamer
    SORTED -> Tester
AttributeRenamer
    ATTR_TABLE = RENAME_SET_DEFAULT td_adressomradesnamn > text
    MISSING_INPUT_ATTRS = REMOVE
    -> Junction
Tester
    BOOL_OP = OR
    TEST_CLAUSE = TEST td_gardsadressomradesnamn ATTRIBUTE_HAS_A_VALUE ""
    TEST_MODE = TEST
    PASSED -> AttributeRenamer_2
AttributeRenamer_2
    ATTR_TABLE = RENAME_SET_DEFAULT td_gardsadressomradesnamn > text
    MISSING_INPUT_ATTRS = REMOVE
    -> Junction
Junction
    -> LineBuilder
    -> StringConcatenator_2
LineBuilder
    ACCUM_INPUT_ATTRS = Use Attributes From One Feature
    GROUP_BY = bal_typ text
    REMOVE_DUPLICATES = Yes
    POINT -> StringConcatenator_36
    LINE -> StringConcatenator_36
    <REJECTED> -> <Rejected> (output)
StringConcatenator_36
    ACTION = Create New Attribute
    PARM_LINE = fme_basicstring:13%15:adressområde @Value(bal_typ)
    VAL_ATTR = typ
    -> AttributeManager_6
Note: AttributeManager_6 [AttributeManager] / Attribute Actions: Input AttributeOutput AttributeAttribute ValueActionsourcetd_bal.bal_adressplats_pSet Valuebal_nummerbal_nummerRemovebal_bokstavstillaggbal_bokstavstillaggRemovebal_typbal_typRemovetd_adressomradesnamntd_adressomradesnamnRemovetd_gardsadressomradesnamntd_gardsadressomradesnamnRemove
AttributeManager_6
    ATTR_TABLE:
      SET_TO source = td_bal.bal_adressplats_p
      REMOVE bal_nummer
      REMOVE bal_bokstavstillagg
      REMOVE bal_typ
      REMOVE td_adressomradesnamn
      REMOVE td_gardsadressomradesnamn
    -> StringCaseChanger_5
StringCaseChanger_5
    ATTRCHOICE = Selected Attributes
    ATTRLIST = typ
    CHANGE_TYPE = lowercase
    -> SearchBoundingBoxAndPoint_3
SearchBoundingBoxAndPoint_3
    ATTRIBUTES = source text typ
    RotDirectory = ../
    BoundingBox -> AttributeCreator_2
    point -> AttributeCreator_3
    <Rejected> -> <Rejected> (output)
StringConcatenator_2
    ACTION = Create New Attribute
    PARM_LINE = fme_basicstring:13%15:adressområde @Value(bal_typ)
    VAL_ATTR = typ
    -> AttributeManager_10
Note: AttributeManager_10 [AttributeManager] / Attribute Actions: Input AttributeOutput AttributeAttribute ValueActionsourcetd_bal.bal_adressplats_pSet Valuebal_nummerbal_nummerRemovebal_bokstavstillaggbal_bokstavstillaggRemovebal_typbal_typRemovetd_adressomradesnamntd_adressomradesnamnRemovetd_gardsadressomradesnamntd_gardsadressomradesnamnRemove
AttributeManager_10
    ATTR_TABLE:
      SET_TO source = td_bal.bal_adressplats_p
      REMOVE bal_nummer
      REMOVE bal_bokstavstillagg
      REMOVE bal_typ
      REMOVE td_adressomradesnamn
      REMOVE td_gardsadressomradesnamn
    -> StringCaseChanger_10
StringCaseChanger_10
    ATTRCHOICE = Selected Attributes
    ATTRLIST = typ
    CHANGE_TYPE = lowercase
    -> HullAccumulator
HullAccumulator
    3DMODE_PARAM = 2D
    ACCUM_INPUT_ATTRS = Use Attributes From One Feature
    GROUP_BY = source text typ
    HULLTYPE_PARAM = Concave )(
    HULL -> AttributeCreator_7
    <REJECTED> -> <Rejected> (output)

Bookmark: bygggnadsnamn
FeatureReader_2
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_2
    <REJECTED> -> <Rejected> (output)
AttributeExposer_2
    ATTR_LIST = bal_namn
    -> Tester_2
Tester_2
    BOOL_OP = OR
    TEST_CLAUSE = TEST bal_namn ATTRIBUTE_HAS_A_VALUE ""
    TEST_MODE = TEST
    PASSED -> Tester_11
Tester_11
    BOOL_OP = OR
    TEST_CLAUSE = CASE_INSENSITIVE_TEST @Value(bal_namn) CONTAINS
    TEST_MODE = TEST
    PASSED -> AttributeSplitter_2
    FAILED -> AttributeSplitter
AttributeSplitter_2
    ATTR_NAME = bal_namn
    DELIMITER = "\n"
    DROP_EMPTY_PARTS = Yes
    LIST_NAME = _linefeed
    TRIM_OPTION = Both
    -> ListExploder
ListExploder
    ATTR_ACCUM_MODE = Merge List Attributes
    ATTR_CONFLICT_RES = Use List Attribute Values
    LIST_ATTR = _linefeed{}
    ELEMENTS -> AttributeCopier
    <REJECTED> -> <Rejected> (output)
AttributeCopier
    ATTR_TABLE = COPY _linefeed > bal_namn
    MISSING_INPUT_ATTRS = REMOVE
    -> AttributeSplitter
AttributeSplitter
    ATTR_NAME = bal_namn
    DELIMITER = ": "
    DROP_EMPTY_PARTS = Yes
    LIST_NAME = _bal_namn
    TRIM_OPTION = Both
    -> AttributeCreator_6
AttributeCreator_6
    ATTR_TABLE:
      SET_TO _bal_namn_1 = @Value(_bal_namn{0})
      SET_TO _bal_namn_2 = @Value(_bal_namn{1})
    -> StringCaseChanger
StringCaseChanger
    ATTRCHOICE = Selected Attributes
    ATTRLIST = _bal_namn_1
    CHANGE_TYPE = lowercase
    -> StringConcatenator
StringConcatenator
    ACTION = Create New Attribute
    PARM_LINE = fme_basicstring:13%19:byggnadsnamn @Value(_bal_namn_1)
    VAL_ATTR = typ
    -> AttributeManager_2
Note: AttributeManager_2 [AttributeManager] / Attribute Actions: Input AttributeOutput AttributeAttribute ValueActionsourcetd_bal.bal_byggnad_ySet Value_bal_namn_2textRenamebal_namnbal_namnRemove_bal_namn_1_bal_namn_1Remove_bal_namn{}_bal_namn{}Remove_linefeed_linefeedRemove
AttributeManager_2
    ATTR_TABLE:
      SET_TO source = td_bal.bal_byggnad_y
      RENAME_SET_VALUE _bal_namn_2 > text
      REMOVE bal_namn
      REMOVE _bal_namn_1
      REMOVE _bal_namn{}
      REMOVE _linefeed
    -> SearchBoundingBoxAndPoint_4
SearchBoundingBoxAndPoint_4
    ATTRIBUTES = source text typ
    RotDirectory = ../
    BoundingBox -> AttributeCreator_2
    BoundingBox -> AttributeCreator_7
    point -> AttributeCreator_3
    <Rejected> -> <Rejected> (output)

Bookmark: markanvändning
FeatureReader_3
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_4
    <REJECTED> -> <Rejected> (output)
AttributeExposer_4
    ATTR_LIST = td_notering_text_1,ma_markanvandningtyp
    -> Tester_3
Tester_3
    BOOL_OP = OR
    TEST_CLAUSE = TEST td_notering_text_1 ATTRIBUTE_HAS_A_VALUE ""
    TEST_MODE = TEST
    PASSED -> AttributeManager_3
Note: AttributeManager_3 [AttributeManager] / Attribute Actions: Input AttributeOutput AttributeAttribute ValueAction_filterValue_filterValueRemovesourcetd_baskarta.ma_markanvandningyta_ySet Valuema_markanvandningtyptypRenametd_notering_text_1textRename
AttributeManager_3
    ATTR_TABLE:
      REMOVE _filterValue
      SET_TO source = td_baskarta.ma_markanvandningyta_y
      RENAME_SET_VALUE ma_markanvandningtyp > typ
      RENAME_SET_VALUE td_notering_text_1 > text
    -> StringCaseChanger_6
StringCaseChanger_6
    ATTRCHOICE = Selected Attributes
    ATTRLIST = typ
    CHANGE_TYPE = lowercase
    -> SearchBoundingBoxAndPoint_5
SearchBoundingBoxAndPoint_5
    ATTRIBUTES = source text typ
    RotDirectory = ../
    BoundingBox -> AttributeCreator_2
    BoundingBox -> AttributeCreator_7
    point -> AttributeCreator_3
    <Rejected> -> <Rejected> (output)

Bookmark: markdetalj
FeatureReader_6
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeCreator
    <REJECTED> -> <Rejected> (output)
AttributeCreator
    ATTR_TABLE = SET_TO source = td_baskarta.md_markdetalj_l
    -> AttributeExposer_5
FeatureReader_5
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeCreator_5
    <REJECTED> -> <Rejected> (output)
AttributeCreator_5
    ATTR_TABLE = SET_TO source = td_baskarta.md_markdetalj_y
    -> AttributeExposer_5
AttributeExposer_5
    ATTR_LIST = td_notering_text_1
    -> Tester_4
Tester_4
    BOOL_OP = OR
    TEST_CLAUSE = TEST td_notering_text_1 ATTRIBUTE_HAS_A_VALUE ""
    TEST_MODE = TEST
    PASSED -> AttributeManager_7
Note: AttributeManager_7 [AttributeManager] / Attribute Actions: Input AttributeOutput AttributeAttribute ValueAction_filterValue_filterValueRemovetypmarkdetaljSet Valuetd_notering_text_1textRename
AttributeManager_7
    ATTR_TABLE:
      REMOVE _filterValue
      SET_TO typ = markdetalj
      RENAME_SET_VALUE td_notering_text_1 > text
    -> StringCaseChanger_7
StringCaseChanger_7
    ATTRCHOICE = Selected Attributes
    ATTRLIST = typ
    CHANGE_TYPE = lowercase
    -> SearchBoundingBoxAndPoint_6
SearchBoundingBoxAndPoint_6
    ATTRIBUTES = source text typ
    RotDirectory = ../
    BoundingBox -> AttributeCreator_2
    BoundingBox -> AttributeCreator_7
    point -> AttributeCreator_3
    <Rejected> -> <Rejected> (output)

Bookmark: marktäcke
FeatureReader_7
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_6
    <REJECTED> -> <Rejected> (output)
AttributeExposer_6
    ATTR_LIST = mt_namnmarktackeobjekt,mt_marktacketyp
    -> Tester_7
Tester_7
    BOOL_OP = OR
    TEST_CLAUSE = TEST mt_namnmarktackeobjekt ATTRIBUTE_HAS_A_VALUE ""
    TEST_MODE = TEST
    PASSED -> AttributeManager_8
Note: AttributeManager_8 [AttributeManager] / Attribute Actions: Input AttributeOutput AttributeAttribute ValueAction_filterValue_filterValueRemovesourcetd_baskarta.mt_marktackeyta_ySet Valuemt_marktacketyptypRenamemt_namnmarktackeobjekttextRename
AttributeManager_8
    ATTR_TABLE:
      REMOVE _filterValue
      SET_TO source = td_baskarta.mt_marktackeyta_y
      RENAME_SET_VALUE mt_marktacketyp > typ
      RENAME_SET_VALUE mt_namnmarktackeobjekt > text
    -> StringCaseChanger_8
StringCaseChanger_8
    ATTRCHOICE = Selected Attributes
    ATTRLIST = typ
    CHANGE_TYPE = lowercase
    -> SearchBoundingBoxAndPoint_7
SearchBoundingBoxAndPoint_7
    ATTRIBUTES = source text typ
    RotDirectory = ../
    BoundingBox -> AttributeCreator_2
    BoundingBox -> AttributeCreator_7
    point -> AttributeCreator_3
    <Rejected> -> <Rejected> (output)

Bookmark: namn
FeatureReader_8
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_7
    <REJECTED> -> <Rejected> (output)
AttributeExposer_7
    ATTR_LIST = td_namntyp,td_namn_1,td_namn_2
    -> Tester_10
Note: Tester_10 [Tester] / Test Clauses: LogicLeft ValueOperatorRight ValueNOT@Value(td_namntyp)=UpplysningstextAND NOT@Value(td_namntyp)=VägnummerAdvanced: / Preserve Feature Order: Per Output Port
Tester_10
    BOOL_OP = AND
    TEST_CLAUSE:
      TEST @Value(td_namntyp) NOT_= Upplysningstext
      TEST @Value(td_namntyp) NOT_= Vägnummer
    TEST_MODE = TEST
    PASSED -> Tester_8
    PASSED -> Tester_9
Note: Tester_8 [Tester] / Test Clauses: Left ValueOperatorRight Value@Value(td_namn_1)Attribute Has a ValueAdvanced: / Preserve Feature Order: Per Output Port
Tester_8
    BOOL_OP = OR
    TEST_CLAUSE = TEST td_namn_1 ATTRIBUTE_HAS_A_VALUE ""
    TEST_MODE = TEST
    PASSED -> AttributeRenamer_3
AttributeRenamer_3
    ATTR_TABLE = RENAME_SET_DEFAULT td_namn_1 > text
    MISSING_INPUT_ATTRS = REMOVE
    -> AttributeManager_9
Note: Tester_9 [Tester] / Test Clauses: Left ValueOperatorRight Value@Value(td_namn_2)Attribute Has a ValueAdvanced: / Preserve Feature Order: Per Output Port
Tester_9
    BOOL_OP = OR
    TEST_CLAUSE = TEST td_namn_2 ATTRIBUTE_HAS_A_VALUE ""
    TEST_MODE = TEST
    PASSED -> AttributeRenamer_4
AttributeRenamer_4
    ATTR_TABLE = RENAME_SET_DEFAULT td_namn_2 > text
    MISSING_INPUT_ATTRS = REMOVE
    -> AttributeManager_9
Note: AttributeManager_9 [AttributeManager] / Attribute Actions: Input AttributeOutput AttributeAttribute ValueAction_filterValue_filterValueRemovesourcetd_baskarta.td_namn_pSet Valuetd_namntyptypRenametd_namn_1td_namn_1Removetd_namn_2td_namn_2Remove
AttributeManager_9
    ATTR_TABLE:
      REMOVE _filterValue
      SET_TO source = td_baskarta.td_namn_p
      RENAME_SET_VALUE td_namntyp > typ
      REMOVE td_namn_1
      REMOVE td_namn_2
    -> StringCaseChanger_9
StringCaseChanger_9
    ATTRCHOICE = Selected Attributes
    ATTRLIST = typ
    CHANGE_TYPE = lowercase
    -> SearchBoundingBoxAndPoint_8
SearchBoundingBoxAndPoint_8
    ATTRIBUTES = source text typ
    RotDirectory = ../
    BoundingBox -> AttributeCreator_2
    BoundingBox -> AttributeCreator_7
    point -> AttributeCreator_3
    <Rejected> -> <Rejected> (output)

Bookmark: Hanterar då linje eller punkt skapats av hull-generering
Note: Punkt eller linje kan uppstå vid konvext hölje när punktobjekt är färre än 3
GeometryFilter
    BREAK_AGG = No
    GEOM_PORT_NAMES = Point Line
    POINT -> Bufferer
    LINE -> Bufferer
    <UNFILTERED> -> ThickenThinPolygon_2
Bufferer
    ANGLE = 22.5
    CAP_STYLE = Arc
    CORNER_STYLE = Arc
    MODE = AREA
    OFFSET = 1
    OFFSET_UNITS = NONE
    PRECISION = APPROX
    BUFFERED -> AttributeCreator_4
    <REJECTED> -> <Rejected> (output)

FME custom transformer ArcStrokerRefiner2D

Input (input)
    -> ArcStroker
Note: ArcStroker [ArcStroker] / General: / Stroke By: Maximum Deviation / Maximum Deviation: 0.02 / Make Polygon Out of 360 Degree Arcs: No
ArcStroker
    MAKE_POLY = No
    STROKE_CHOICE = Maximum Deviation
    TOLERANCE_VAL = 0.02
    STROKED -> 2DForcer
2DForcer
    2D -> GeometryRefiner
GeometryRefiner
    -> Output (output)
Output (output)

FME custom transformer ThickenThinPolygon

Parameters:
- IsRectangle =   # Geometrin är rektangel
- Buffer =   # Buffer (m)

Input (input)
    -> ParameterFetcher
ParameterFetcher
    ATTR_LIST = _IsRectangle $(IsRectangle) _Buffer $(Buffer)
    -> Tester
Note: Om någon sida är kortare än buffertavståndet, bredda objektet genom buffring och behålla rektangel
Tester_2
    BOOL_OP = OR
    TEST_CLAUSE:
      TEST @Value(_sideLength_A) < @Value(_Buffer)
      TEST @Value(_sideLength_B) < @Value(_Buffer)
    TEST_MODE = TEST
    PASSED -> AttributeCreator_5
    FAILED -> Tester_4
Tester_4
    BOOL_OP = OR
    TEST_CLAUSE = TEST @Value(_IsRectangle) = YES
    TEST_MODE = TEST
    PASSED -> Output (output)
    FAILED -> GeometryReplacer
GeometryReplacer
    KIND_LONG = FME Binary
    REMOVE_ATTRIBUTE = No
    SOURCE = @Value(_geometry)
    -> Output (output)
    <REJECTED> -> <Rejected> (output)
Output (output)
<Rejected> (output)

Bookmark: Hantering rektangel
Note: Om rektangel, gå vidare. Annars om inte rektangel, kopiera undan originalgeometrin för senare och konvertera till boundingbox-rektangel
Tester
    BOOL_OP = OR
    TEST_CLAUSE = TEST @Value(_IsRectangle) = YES
    TEST_MODE = TEST
    PASSED -> CoordinateExtractor
    FAILED -> GeometryExtractor
GeometryExtractor
    ATTR = _geometry
    KIND_LONG = FME Binary
    REMOVE_GEOMETRY = No
    -> BoundingBoxReplacer
BoundingBoxReplacer
    BOXTYPE = 2D Oriented Bounding Box
    BOX -> CoordinateExtractor
CoordinateExtractor
    LIST_NAME = _indices
    MODE = All Coordinates
    -> ExpressionEvaluator
    <REJECTED> -> <Rejected> (output)

Bookmark: Räkna ut rektangelns sidlängder
ExpressionEvaluator
    ACTION = Create New Attribute
    EXPRESSION:
      @sqrt(
          @pow(@abs((@Value(_indices{0}.x)-@Value(_indices{1}.x))),2) +
          @pow(@abs((@Value(_indices{0}.y)-@Value(_indices{1}.y))),2)
      )
    VAL_ATTR = _sideLength_A
    -> ExpressionEvaluator_2
ExpressionEvaluator_2
    ACTION = Create New Attribute
    EXPRESSION:
      @sqrt(
          @pow(@abs((@Value(_indices{1}.x)-@Value(_indices{2}.x))),2) +
          @pow(@abs((@Value(_indices{1}.y)-@Value(_indices{2}.y))),2)
      )
    VAL_ATTR = _sideLength_B
    -> Tester_2

Bookmark: Buffrar utifrån kortaste sidan
AttributeCreator_5
    ATTR_TABLE = SET_TO _ShortestSide = FME_CONDITIONAL:DEFAULT_VALUE'B'BOOL_OP;OR;COMPOSITE_TEST;1;TEST @Value(_sideLength_A) < @Value(_sideLength_B)'A'FME_NUM_CONDITIONS2___
    -> Tester_3
Tester_3
    BOOL_OP = OR
    TEST_CLAUSE = TEST @Value(_ShortestSide) = A
    TEST_MODE = TEST
    PASSED -> Bufferer_3
    FAILED -> Bufferer_2
Bufferer_3
    ANGLE = 22.5
    CAP_STYLE = Arc
    CORNER_STYLE = Arc
    MODE = AREA
    OFFSET = @Value(_Buffer)-@Value(_sideLength_A)
    OFFSET_UNITS = NONE
    PRECISION = APPROX
    BUFFERED -> Output (output)
    <REJECTED> -> <Rejected> (output)
Bufferer_2
    ANGLE = 22.5
    CAP_STYLE = Arc
    CORNER_STYLE = Arc
    MODE = AREA
    OFFSET = @Value(_Buffer)-@Value(_sideLength_B)
    OFFSET_UNITS = NONE
    PRECISION = APPROX
    BUFFERED -> Output (output)
    <REJECTED> -> <Rejected> (output)

FME custom transformer Plan_och_Tomt

Parameters:
- RotDirectory = ../   # Katalogen där processen startar
- ProcessModulName =   # Processmodulsnamn
- OutSchemaFileNameSuffix = flush   # Suffix på filnamn för schemalistning (skapas med bindestreck)
- PlandokumentDir =   # Katalog plandokument
- PlandokumentFileFilter =   # Filfilter
- PlandokumentDir3Rd =   # Katalog plandokument 3:e
- DATASET = @Value(Dataset)   # Dataset
- _FILTERVALUE = @Value(_filterValue)   # Filtervalue
- FME_FORMAT_SHORT_NAME = @Value(fme_format_short_name)   # Fme Format Short Name
- FME_FEATURE_TYPE_NAME = @Value(fme_feature_type_name)   # Fme Feature Type Name

Input (input)
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(_filterValue) = td_drk.rk_plan_y",td_drk.rk_plan_y,"BOOL_OP,OR,COMPOSITE_TEST,""""""1"""""",TEST_CLAUSE,TEST @Value(_filterValue) = td_drk.rk_plan_y_info",td_drk.rk_plan_y_info,"BOOL_OP,OR,COMPOSITE_TEST,""""""1"""""",TEST_CLAUSE,TEST @Value(_filterValue) = dbo.off_fir_plan",dbo.off_fir_plan,"BOOL_OP,OR,COMPOSITE_TEST,""""""1"""""",TEST_CLAUSE,TEST @Value(_filterValue) = dbo.off_fir_plan_beslut",dbo.off_fir_plan_beslut,"BOOL_OP,OR,COMPOSITE_TEST,""""""1"""""",TEST_CLAUSE,TEST @Value(_filterValue) = dbo.fir_plan_egnauppg",dbo.fir_plan_egnauppg,"BOOL_OP,OR,COMPOSITE_TEST,""""""1"""""",TEST_CLAUSE,TEST @Value(_filterValue) = dbo.fir_firkoder",dbo.fir_firkoder,"BOOL_OP,OR,COMPOSITE_TEST,""""""1"""""",TEST_CLAUSE,TEST @Value(_filterValue) = dbo.off_fir_plan_kommun",dbo.off_fir_plan_kommun,"BOOL_OP,OR,COMPOSITE_TEST,""""""1"""""",TEST_CLAUSE,TEST @Value(_filterValue) = dbo.off_fir_plan_hanvisn",dbo.off_fir_plan_hanvisn,"BOOL_OP,OR,COMPOSITE_TEST,""""""1"""""",TEST_CLAUSE,TEST @Value(_filterValue) = dbo.off_fir_plan_hanvtext",dbo.off_fir_plan_hanvtext
    td_drk.rk_plan_y -> FeatureReader_2 [INITIATOR]
    td_drk.rk_plan_y_info -> FeatureReader_5 [INITIATOR]
    dbo.off_fir_plan -> FeatureReader_4 [INITIATOR]
    dbo.off_fir_plan_beslut -> FeatureReader_6 [INITIATOR]
    dbo.fir_plan_egnauppg -> FeatureReader_7 [INITIATOR]
    dbo.fir_firkoder -> FeatureReader_3 [INITIATOR]
    dbo.off_fir_plan_kommun -> FeatureReader_8 [INITIATOR]
    dbo.off_fir_plan_hanvisn -> FeatureReader_10 [INITIATOR]
    dbo.off_fir_plan_hanvtext -> FeatureReader_11 [INITIATOR]
    <UNFILTERED> -> Junction_53
Junction_24
    -> <Rejected> (output)
Junction_6
    -> <Rejected> (output)
Junction_21
    -> Junction_22
Junction_22
    -> <Rejected> (output)
Junction_53
    -> Junction_61
Junction_61
    -> <Rejected> (output)
Junction_38
    -> <Rejected> (output)
Junction_19
    -> <Rejected> (output)
Junction_41
    -> <Rejected> (output)
Junction_35
    -> <Rejected> (output)
Junction_15
    -> <Rejected> (output)
Junction_8
    -> <Rejected> (output)
Junction_11
    -> <Rejected> (output)
Junction_36
    -> <Rejected> (output)
Junction_40
    -> <Rejected> (output)
Junction_30
    -> <Rejected> (output)
Junction_34
    -> <Rejected> (output)
Junction_28
    -> <Rejected> (output)
Junction_18
    -> <Rejected> (output)
Junction_26
    -> <Rejected> (output)
Junction_32
    -> <Rejected> (output)
Junction_56
    -> <Rejected> (output)
Junction_52
    -> <Rejected> (output)
Note: Tester_6 [Tester] / Test Clauses: Left ValueOperatorRight Value@Value(lmakt)Attribute Has a ValueAdvanced: / Preserve Feature Order: Per Output Port
Note: Förekommer bestämmelser utan aktbeteckning. Bestämmelsenycklarna saknar motsvarigheter i registerkartan.
Tester_6
    BOOL_OP = OR
    TEST_CLAUSE = TEST lmakt ATTRIBUTE_HAS_A_VALUE ""
    TEST_MODE = TEST
    PASSED -> FeatureMerger_2 [SUPPLIER]
FeatureMerger_2
    ATTR_ACCUM_MODE = Merge Supplier
    ATTR_CONFLICT_RES = Use Requestor
    IGNORE_NULLS = No
    JOIN_KEYS = @Value(rk_extid) @Value(lmakt) AUTO
    MERGE_TYPE = Attributes Only
    PROCESS_DUPS = NO
    REJECT_NULL_MISSING_KEYS = No
    SUPPLIERS_FIRST = No
    MERGED -> Tester_8
    UNMERGED_REQUESTOR -> Tester_8
    <REJECTED> -> Junction_3
Note: Gällande eller / status saknas / för att få med geometrin när registerenhet saknas
Tester_8
    BOOL_OP = OR
    TEST_CLAUSE:
      TEST @Value(pstatus) = B
      TEST pstatus ATTRIBUTE_IS_MISSING ""
    TEST_MODE = TEST
    PASSED -> AttributeFilter_2
AttributeManager_3
    ATTR_TABLE:
      SET_TO fme_feature_type = plan
      SET_TO fme_feature_type_name = plan
      REMOVE rk_extid
      RENAME_SET_VALUE arkivserie_pb > akt_pb
      RENAME_SET_VALUE pb > plan_id
      RENAME_SET_VALUE lmakt > akt
      RENAME_SET_VALUE pstatus > status
      RENAME_SET_VALUE sajdat > d_senajou
      RENAME_SET_VALUE lagakraft_dat > d_lagakra
      RENAME_SET_VALUE genomf_tilldat > d_genom_t
      RENAME_SET_VALUE genomf_fromdat > d_genom_f
      RENAME_SET_VALUE gallertill_dat > d_gall_t
      RENAME_SET_VALUE beslutsdat > d_beslut
      RENAME_SET_VALUE plannr > akt_egn
      REMOVE kodtyp
      REMOVE kodvarde
      RENAME_SET_VALUE beskrivning > statustxt
      REMOVE komkod{}.komkod
      RENAME_SET_VALUE forbud_tradfallning > tradfallej
      RENAME_SET_VALUE avvikelse > avvik
      RENAME_SET_VALUE avvikelse_dokument > avvik_dok
    -> Sampler
    -> Tester_akt_egn
Note: Trigger
Sampler
    RATE = 1
    SAMPLE_MODE = No
    SAMPLE_TYPE_LONG = First N Features
    SAMPLED -> FeatureReader [INITIATOR]
    SAMPLED -> FeatureReader_12 [INITIATOR]
Note: Plandokument
FeatureReader
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    COMBINE_GEOM = Use Result
    DATASET = $(PlandokumentDir)
    FORMAT = PATH
    OUTPUT_FEATURES_DISPLAY = Schema and Data Features
    PATH_GLOB_PATTERN = $(PlandokumentFileFilter)
    PATH_NO_EMPTY_PROPERTIES = YES
    PATH_OFFSET_DATETIME = yes
    PATH_RECURSE_DIRECTORIES = NO
    PATH_RETRIEVE_FILE_PROPERTIES = NO
    PATH_TYPE = ANY
    PATH_USE_NON_STRING_ATTR = yes
    PATH -> AttributeKeeper
AttributeKeeper
    CREATE_BULK_MODE_FEATURES = No
    KEEP_ATTRS = path_windows,path_extension,path_filename,path_rootname
    -> StringCaseChanger
StringCaseChanger
    ATTRCHOICE = Selected Attributes
    ATTRLIST = path_extension path_filename
    CHANGE_TYPE = lowercase
    -> FeatureMerger_karta [SUPPLIER]
    -> Tester_10
Tester_10
    BOOL_OP = COMPOSITE
    COMPOSITE_TEST = 1 AND ( 2 OR 3 )
    TEST_CLAUSE:
      TEST @Value(path_extension) = pdf
      TEST @Value(path_rootname) CONTAINS_REGEX ^.{6,7}-.{3,5}_\d+(_besk$|_genom$|_pgbesk$|_best$|_kvalprog$|$)
      TEST @Value(path_rootname) CONTAINS_REGEX ^.{5,6}(_besk$|_genom$|_pgbesk$|_best$|_kvalprog$|$)
    TEST_MODE = TEST
    PASSED -> FeatureMerger_15 [REQUESTOR]
Plandokument (output)
Junction_63
    -> <Rejected> (output)
AttributeKeeper_2
    CREATE_BULK_MODE_FEATURES = NO
    KEEP_ATTRS = d_genom_f,akt,planfk,d_beslut,d_genom_t,pav_akt,plannamn,harpkarta,d_lagakra,komkod,harkvalpro,d_gall_t,fme_feature_type_name,planavgift,akt_pb,hargenom,plan_id,statustxt,d_senajou,fme_feature_type,akt_egn,status,harpbest,harpgbesk,pav_p_id,harbesk,hartkarta,pav_akt_br,pav_akt_n,tradfallej,avvik,avvik_dok
    -> AttributeManager_2
AttributeManager_2
    -> AttributeFilter
AttributeFilter
    ATTR_NAME = planfk
    ATTR_VALUES = BPL,DP,OB,SPL,ÄDP,ÄOB,TI,FP,<Empty>,<Missing>,<Null>,<Unfiltered>
    BPL -> Planytor_gällande_alla (output)
    BPL -> Planytor_gällande (output)
    BPL -> CenterPointExtractor
    DP -> Planytor_gällande_alla (output)
    DP -> Planytor_gällande (output)
    DP -> CenterPointExtractor
    OB -> Planytor_gällande_alla (output)
    OB -> Planytor_gällande (output)
    OB -> CenterPointExtractor
    SPL -> Planytor_gällande_alla (output)
    SPL -> Planytor_gällande (output)
    SPL -> CenterPointExtractor
    ÄDP -> Planytor_gällande_alla (output)
    ÄDP -> Planytor_gällande_ändrade (output)
    ÄDP -> CenterPointExtractor
    ÄOB -> Planytor_gällande_alla (output)
    ÄOB -> Planytor_gällande_ändrade (output)
    ÄOB -> CenterPointExtractor
    TI -> Junction_43
    FP -> Junction_43
Planytor_gällande_alla (output)
Planytor_gällande (output)
Planytor_gällande_ändrade (output)
Junction_43
    -> AttributeCreator_8
AttributeCreator_8
    ATTR_TABLE:
      SET_TO fme_feature_type = tomtindelning_fastighetsplan
      SET_TO fme_feature_type_name = tomtindelning_fastighetsplan
    -> Tomtindelning_Fastighetsplan_gällande (output)
    -> CenterPointExtractor_2
Tomtindelning_Fastighetsplan_gällande (output)
CenterPointExtractor_2
    CENTX = _inside_x
    CENTY = _inside_y
    EXTRACTIONMODE = INSIDE
    -> VertexCreator_2
    <REJECTED> -> <Rejected> (output)
VertexCreator_2
    MEASURE_TYPE = Continuous
    MODE_NAME = Replace with Point
    XVAL = @Value(_inside_x)
    YVAL = @Value(_inside_y)
    -> AttributeRemover_3
    <REJECTED> -> <Rejected> (output)
AttributeRemover_3
    REMOVE_ATTRS = _inside_x,_inside_y
    -> Tomtindelning_Fastighetsplan_centroid_gällande (output)
Tomtindelning_Fastighetsplan_centroid_gällande (output)
CenterPointExtractor
    CENTX = _inside_x
    CENTY = _inside_y
    EXTRACTIONMODE = INSIDE
    -> VertexCreator
    <REJECTED> -> Junction
VertexCreator
    MEASURE_TYPE = Continuous
    MODE_NAME = Replace with Point
    XVAL = @Value(_inside_x)
    YVAL = @Value(_inside_y)
    -> AttributeRemover_2
    <REJECTED> -> Junction_10
AttributeRemover_2
    REMOVE_ATTRS = _inside_x,_inside_y
    -> Plancentroid_gällande_alla (output)
Plancentroid_gällande_alla (output)
Junction_10
    -> Junction_42
Junction_42
    -> <Rejected> (output)
Junction
    -> Junction_2
Junction_2
    -> <Rejected> (output)
Junction_46
    -> <Rejected> (output)
Note: UnmergeRequester = loggas varning?, / planer från kartan som ej har motsvarande / UnusedSupplier = loggas varning? / planer från register som ej finns i kartan
Junction_3
    -> Junction_4
Junction_4
    -> <Rejected> (output)
Junction_59
    -> <Rejected> (output)
Junction_54
    -> <Rejected> (output)
<Rejected> (output)

Bookmark: Karta planer
Note: Ytor
FeatureReader_2
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer
    <REJECTED> -> Junction_23
AttributeExposer
    ATTR_LIST = rk_extid,rk_dep
    -> FeatureMerger [REQUESTOR]
Junction_23
    -> Junction_24
Note: Kommuninformation
FeatureReader_5
    ATTR_ACCUM_MODE = Only Use Result
    COMBINE_GEOM = Use Result
    DATASET = @Value(Dataset)
    FEATURETYPES = @Value(fme_feature_type_name)
    FORMAT = POSTGRES
    OUTPUT_FEATURES_DISPLAY = Schema and Data Features
    POSTGRES_CREATE_FEATURE_TABLES_FROM_DATA = Yes
    POSTGRES_FEATURES_PER_FETCH = 10000
    POSTGRES_NAMED_CONNECTION = @Value(Dataset)
    POSTGRES_QUERY_FEATURE_TYPES_FOR_MERGE_FILTERS = Yes
    POSTGRES_READ_TIME_WITH_TIMEZONE = Yes
    <OTHER> -> AttributeExposer_2
    <REJECTED> -> Junction_21
AttributeExposer_2
    ATTR_LIST = rk_extid,arkivserie_pb,planavgift,forbud_tradfallning,avvikelse,avvikelse_dokument
    -> AttributeValueMapper
AttributeValueMapper
    DIRECTION = Forward (Source To Destination)
    LUT = J,Ja,N,Nej,FME_NULL_VALUE,Nej
    SRC = planavgift
    VAL_ATTR = planavgift
    -> AttributeValueMapper_2
AttributeValueMapper_2
    DIRECTION = Forward (Source To Destination)
    LUT = t,Ja,f,Nej,FME_NULL_VALUE,Nej
    SRC = forbud_tradfallning
    VAL_ATTR = forbud_tradfallning
    -> AttributeValueMapper_4
AttributeValueMapper_4
    DIRECTION = Forward (Source To Destination)
    LUT = t,Ja,f,Nej,FME_NULL_VALUE,Nej
    SRC = avvikelse
    VAL_ATTR = avvikelse
    -> FeatureMerger [SUPPLIER]
FeatureMerger
    ATTR_ACCUM_MODE = Merge Supplier
    ATTR_CONFLICT_RES = Use Requestor
    IGNORE_NULLS = No
    JOIN_KEYS = @Value(rk_extid) @Value(rk_extid) AUTO
    MERGE_TYPE = Attributes Only
    PROCESS_DUPS = NO
    REJECT_NULL_MISSING_KEYS = No
    SUPPLIERS_FIRST = No
    MERGED -> FeatureMerger_2 [REQUESTOR]
    UNMERGED_REQUESTOR -> FeatureMerger_2 [REQUESTOR]
    <REJECTED> -> Junction_5
Junction_5
    -> Junction_6

Bookmark: Register
Note: Bestämmelse
FeatureReader_4
    ATTR_ACCUM_MODE = Only Use Result
    COMBINE_GEOM = Use Result
    DATASET = @Value(Dataset)
    FEATURETYPES = @Value(fme_feature_type_name)
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = @Value(Dataset)
    MSSQL_ADO_QUERY_FEATURE_TYPES_FOR_MERGE_FILTERS = Yes
    MSSQL_ADO_READ_CACHE_SIZE = 10
    OUTPUT_FEATURES_DISPLAY = Schema and Data Features
    <OTHER> -> AttributeExposer_3
    <REJECTED> -> Junction_37
AttributeExposer_3
    ATTR_LIST = pb,planfk,lmakt,plannamn,pstatus
    -> Tester_3
Note: Endast gällande planer
Tester_3
    BOOL_OP = OR
    TEST_CLAUSE = TEST @Value(pstatus) = B
    TEST_MODE = TEST
    PASSED -> Junction_44
    PASSED -> FeatureMerger_4 [REQUESTOR]
Junction_37
    -> Junction_38
Note: Datum
FeatureReader_6
    ATTR_ACCUM_MODE = Only Use Result
    COMBINE_GEOM = Use Result
    DATASET = @Value(Dataset)
    FEATURETYPES = @Value(fme_feature_type_name)
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = @Value(Dataset)
    MSSQL_ADO_QUERY_FEATURE_TYPES_FOR_MERGE_FILTERS = Yes
    MSSQL_ADO_READ_CACHE_SIZE = 10
    OUTPUT_FEATURES_DISPLAY = Schema and Data Features
    <OTHER> -> AttributeExposer_4
    <REJECTED> -> Junction_39
AttributeExposer_4
    ATTR_LIST = pb,beslutsdat,genomf_fromdat,genomf_tilldat,gallertill_dat,lagakraft_dat,sajdat
    -> DateHandler
DateHandler
    _ATTRIBUT = beslutsdat
    _DATUM = @Value(beslutsdat)
    _OWERWRITE = Ja
    -> DateHandler_2
    <Rejected> -> Junction_16
Junction_16
    -> Junction_19
DateHandler_2
    _ATTRIBUT = gallertill_dat
    _DATUM = @Value(gallertill_dat)
    _OWERWRITE = Ja
    -> DateHandler_3
    <Rejected> -> Junction_20
Junction_20
    -> Junction_41
DateHandler_3
    _ATTRIBUT = genomf_fromdat
    _DATUM = @Value(genomf_fromdat)
    _OWERWRITE = Ja
    -> DateHandler_4
    <Rejected> -> Junction_14
DateHandler_4
    _ATTRIBUT = genomf_tilldat
    _DATUM = @Value(genomf_tilldat)
    _OWERWRITE = Ja
    -> DateHandler_5
    <Rejected> -> Junction_12
Junction_12
    -> Junction_35
DateHandler_5
    _ATTRIBUT = lagakraft_dat
    _DATUM = @Value(lagakraft_dat)
    _OWERWRITE = Ja
    -> DateHandler_6
    <Rejected> -> Junction_13
Junction_13
    -> Junction_15
DateHandler_6
    _ATTRIBUT = sajdat
    _DATUM = @Value(sajdat)
    _OWERWRITE = Ja
    -> FeatureMerger_4 [SUPPLIER]
    <Rejected> -> Junction_9
FeatureMerger_4
    ATTR_ACCUM_MODE = Merge Supplier
    ATTR_CONFLICT_RES = Use Requestor
    IGNORE_NULLS = No
    JOIN_KEYS = @Value(pb) @Value(pb) AUTO
    MERGE_TYPE = Attributes Only
    PROCESS_DUPS = NO
    REJECT_NULL_MISSING_KEYS = No
    SUPPLIERS_FIRST = No
    MERGED -> FeatureMerger_5 [REQUESTOR]
    UNMERGED_REQUESTOR -> FeatureMerger_5 [REQUESTOR]
    <REJECTED> -> Junction_7
Junction_7
    -> Junction_8
Junction_9
    -> Junction_11
Junction_14
    -> Junction_36
Junction_39
    -> Junction_40
Note: Kommunal planbeteckning
FeatureReader_7
    ATTR_ACCUM_MODE = Only Use Result
    COMBINE_GEOM = Use Result
    DATASET = @Value(Dataset)
    FEATURETYPES = @Value(fme_feature_type_name)
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = @Value(Dataset)
    MSSQL_ADO_QUERY_FEATURE_TYPES_FOR_MERGE_FILTERS = Yes
    MSSQL_ADO_READ_CACHE_SIZE = 10
    OUTPUT_FEATURES_DISPLAY = Schema and Data Features
    <OTHER> -> AttributeExposer_5
    <REJECTED> -> Junction_33
AttributeExposer_5
    ATTR_LIST = pb,plannr
    -> FeatureMerger_5 [SUPPLIER]
FeatureMerger_5
    ATTR_ACCUM_MODE = Merge Supplier
    ATTR_CONFLICT_RES = Use Requestor
    IGNORE_NULLS = No
    JOIN_KEYS = @Value(pb) @Value(pb) AUTO
    MERGE_TYPE = Attributes Only
    PROCESS_DUPS = NO
    REJECT_NULL_MISSING_KEYS = No
    SUPPLIERS_FIRST = No
    MERGED -> FeatureMerger_3 [REQUESTOR]
    UNMERGED_REQUESTOR -> FeatureMerger_3 [REQUESTOR]
    <REJECTED> -> Junction_29
Junction_29
    -> Junction_30
Junction_33
    -> Junction_34
Note: Statuskoder
FeatureReader_3
    ATTR_ACCUM_MODE = Only Use Result
    COMBINE_GEOM = Use Result
    DATASET = @Value(Dataset)
    FEATURETYPES = @Value(fme_feature_type_name)
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = @Value(Dataset)
    MSSQL_ADO_QUERY_FEATURE_TYPES_FOR_MERGE_FILTERS = Yes
    MSSQL_ADO_READ_CACHE_SIZE = 10
    OUTPUT_FEATURES_DISPLAY = Schema and Data Features
    <OTHER> -> AttributeExposer_6
    <REJECTED> -> Junction_17
AttributeExposer_6
    ATTR_LIST = kodtyp,kodvarde,beskrivning
    -> Tester
    -> Tester_2
Tester
    BOOL_OP = OR
    TEST_CLAUSE = TEST @Value(kodtyp) = PSTATUS
    TEST_MODE = TEST
    PASSED -> FeatureMerger_3 [SUPPLIER]
FeatureMerger_3
    ATTR_ACCUM_MODE = Merge Supplier
    ATTR_CONFLICT_RES = Use Requestor
    IGNORE_NULLS = No
    JOIN_KEYS = @Value(pstatus) @Value(kodvarde) AUTO
    MERGE_TYPE = Attributes Only
    PROCESS_DUPS = NO
    REJECT_NULL_MISSING_KEYS = No
    SUPPLIERS_FIRST = No
    MERGED -> FeatureMerger_6 [REQUESTOR]
    UNMERGED_REQUESTOR -> FeatureMerger_6 [REQUESTOR]
    <REJECTED> -> Junction_27
Junction_27
    -> Junction_28
Junction_17
    -> Junction_18
Note: Kommunkod till plan
FeatureReader_8
    ATTR_ACCUM_MODE = Only Use Result
    COMBINE_GEOM = Use Result
    DATASET = @Value(Dataset)
    FEATURETYPES = @Value(fme_feature_type_name)
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = @Value(Dataset)
    MSSQL_ADO_QUERY_FEATURE_TYPES_FOR_MERGE_FILTERS = Yes
    MSSQL_ADO_READ_CACHE_SIZE = 10
    OUTPUT_FEATURES_DISPLAY = Schema and Data Features
    <OTHER> -> AttributeExposer_7
    <REJECTED> -> Junction_31
AttributeExposer_7
    ATTR_LIST = pb,komkod
    -> FeatureMerger_6 [SUPPLIER]
FeatureMerger_6
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(pb) @Value(pb) AUTO
    LIST_ATTRS_TO_INCLUDE = komkod
    LIST_NAME = komkod
    MERGE_TYPE = Attributes Only
    PROCESS_DUPS = YES
    REJECT_NULL_MISSING_KEYS = No
    SUPPLIERS_FIRST = No
    MERGED -> TestFilter_6
    UNMERGED_REQUESTOR -> TestFilter_6
    <REJECTED> -> Junction_25
Junction_25
    -> Junction_26
Junction_31
    -> Junction_32

Bookmark: Påverkan av andra planer och beslut
Junction_44
    -> FeatureMerger_12 [SUPPLIER]
    -> Tester_4
    -> FeatureMerger_11 [SUPPLIER]
Tester_2
    BOOL_OP = OR
    TEST_CLAUSE = TEST @Value(kodtyp) = HANVTYP
    TEST_MODE = TEST
    PASSED -> FeatureMerger_8 [SUPPLIER]
    PASSED -> FeatureMerger_9 [SUPPLIER]
TestFilter_6
    DEFAULT_VALUE = <UNFILTERED>
    PASSED_TEST_GROUP_OUTPUT = FIRST
    TEST_LIST = "BOOL_OP,OR,COMPOSITE_TEST,""""""1"""""",TEST_CLAUSE,TEST @Value(planfk) = ÄDP",ÄDP,"BOOL_OP,OR,COMPOSITE_TEST,""""""1"""""",TEST_CLAUSE,TEST @Value(planfk) = ÄOB",ÄOB
    ÄDP -> FeatureMerger_13 [REQUESTOR]
    ÄOB -> FeatureMerger_13 [REQUESTOR]
    <UNFILTERED> -> FeatureMerger_10 [REQUESTOR]
Note: För icke ändrade, endast de som blivit ändrade genom ÄDP eller ÄOB. / För ÄDP och ÄOB, de som ändras.
Note: påverkan andra registrerade planer
FeatureReader_10
    ATTR_ACCUM_MODE = Only Use Result
    COMBINE_GEOM = Use Result
    DATASET = @Value(Dataset)
    FEATURETYPES = @Value(fme_feature_type_name)
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = @Value(Dataset)
    MSSQL_ADO_QUERY_FEATURE_TYPES_FOR_MERGE_FILTERS = Yes
    MSSQL_ADO_READ_CACHE_SIZE = 10
    OUTPUT_FEATURES_DISPLAY = Schema and Data Features
    <OTHER> -> AttributeExposer_8
    <REJECTED> -> Junction_55
AttributeExposer_8
    ATTR_LIST = pb,pb_hanvisn,hanvtyp
    -> AttributeCreator_27
AttributeCreator_27
    ATTR_TABLE = SET_TO registrerat_beslut = 1
    -> FeatureMerger_8 [REQUESTOR]
FeatureMerger_8
    ATTR_ACCUM_MODE = Merge Supplier
    ATTR_CONFLICT_RES = Use Requestor
    IGNORE_NULLS = No
    JOIN_KEYS = @Value(hanvtyp) @Value(kodvarde) AUTO
    MERGE_TYPE = Attributes Only
    PROCESS_DUPS = NO
    REJECT_NULL_MISSING_KEYS = No
    SUPPLIERS_FIRST = No
    MERGED -> FeatureMerger_11 [REQUESTOR]
    UNMERGED_REQUESTOR -> FeatureMerger_11 [REQUESTOR]
FeatureMerger_11
    ATTR_ACCUM_MODE = Prefix Supplier
    IGNORE_NULLS = No
    JOIN_KEYS = @Value(pb_hanvisn) @Value(pb) AUTO
    MERGE_TYPE = Attributes Only
    PROCESS_DUPS = NO
    REJECT_NULL_MISSING_KEYS = No
    SUPPLIERS_FIRST = No
    SUPPLIER_PREFIX = pav_
    MERGED -> StringConcatenator_13
StringConcatenator_13
    ACTION = Create New Attribute
    PARM_LINE = fme_basicstring:18%1:@Value(pav_planfk)
    VAL_ATTR = _pav_planfk_txt
    -> AttributeKeeper_4
Junction_55
    -> Junction_56
Note: påverkan andra beslut
FeatureReader_11
    ATTR_ACCUM_MODE = Only Use Result
    COMBINE_GEOM = Use Result
    DATASET = @Value(Dataset)
    FEATURETYPES = @Value(fme_feature_type_name)
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = @Value(Dataset)
    MSSQL_ADO_QUERY_FEATURE_TYPES_FOR_MERGE_FILTERS = Yes
    MSSQL_ADO_READ_CACHE_SIZE = 10
    OUTPUT_FEATURES_DISPLAY = Schema and Data Features
    <OTHER> -> AttributeExposer_9
    <REJECTED> -> Junction_51
AttributeExposer_9
    ATTR_LIST = pb,hanvtext,hanvtyp
    -> AttributeCreator_28
AttributeCreator_28
    ATTR_TABLE = SET_TO registrerat_beslut = 0
    -> FeatureMerger_9 [REQUESTOR]
FeatureMerger_9
    ATTR_ACCUM_MODE = Merge Supplier
    ATTR_CONFLICT_RES = Use Requestor
    IGNORE_NULLS = No
    JOIN_KEYS = @Value(hanvtyp) @Value(kodvarde) AUTO
    MERGE_TYPE = Attributes Only
    PROCESS_DUPS = NO
    REJECT_NULL_MISSING_KEYS = No
    SUPPLIERS_FIRST = No
    MERGED -> FeatureMerger_12 [REQUESTOR]
    UNMERGED_REQUESTOR -> FeatureMerger_12 [REQUESTOR]
FeatureMerger_12
    ATTR_ACCUM_MODE = Prefix Supplier
    IGNORE_NULLS = No
    JOIN_KEYS = @Value(pb) @Value(pb) AUTO
    MERGE_TYPE = Attributes Only
    PROCESS_DUPS = NO
    REJECT_NULL_MISSING_KEYS = No
    SUPPLIERS_FIRST = No
    SUPPLIER_PREFIX = p_
    MERGED -> FeatureMerger_14 [REQUESTOR]
AttributeRenamer
    ATTR_TABLE = RENAME_SET_DEFAULT pav_pb > pb_hanvisn
    MISSING_INPUT_ATTRS = PRESERVE
    -> AttributeCopier
AttributeCopier
    ATTR_TABLE = COPY hanvtext > pav_lmakt
    MISSING_INPUT_ATTRS = PRESERVE
    -> Tester_5
Tester_5
    BOOL_OP = OR
    TEST_CLAUSE = TEST pav_planfk ATTRIBUTE_HAS_A_VALUE ""
    TEST_MODE = TEST
    PASSED -> StringConcatenator_12
    FAILED -> AttributeRenamer_3
StringConcatenator_12
    ACTION = Create New Attribute
    PARM_LINE = fme_basicstring:18%1:@Value(pav_planfk)
    VAL_ATTR = _pav_planfk_txt
    -> Junction_60
AttributeRenamer_3
    ATTR_TABLE = RENAME_SET_DEFAULT pav_planfk > _pav_planfk_txt
    MISSING_INPUT_ATTRS = PRESERVE
    -> Junction_60
Junction_60
    -> AttributeKeeper_4
AttributeKeeper_4
    CREATE_BULK_MODE_FEATURES = NO
    KEEP_ATTRS = _pav_planfk_txt,beskrivning,hanvtyp,kodtyp,kodvarde,pav_lmakt,pav_planfk,pb,pb_hanvisn,registrerat_beslut
    -> StringConcatenator_14
StringConcatenator_14
    ACTION = Create New Attribute
    PARM_LINE = fme_basicstring:19%1:@Value(beskrivning)
    VAL_ATTR = _pav_beskrivning_txt
    -> StringConcatenator_11
StringConcatenator_11
    ACTION = Create New Attribute
    PARM_LINE = fme_basicstring:28%23%17:@Value(_pav_beskrivning_txt)@Value(_pav_planfk_txt)@Value(pav_lmakt)
    VAL_ATTR = _pav_akt
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(kodvarde) = 1",ändrad av (1),"BOOL_OP,OR,COMPOSITE_TEST,""""""1"""""",TEST_CLAUSE,TEST @Value(kodvarde) = 2",upphävd av (2),"BOOL_OP,OR,COMPOSITE_TEST,""""""1"""""",TEST_CLAUSE,TEST @Value(kodvarde) = 5",har koppling till (5),"BOOL_OP,OR,COMPOSITE_TEST,""""""1"""""",TEST_CLAUSE,TEST @Value(kodvarde) = 6",består av (6)
    ändrad av (1) -> TestFilter_5
    upphävd av (2) -> TestFilter_5
    har koppling till (5) -> TestFilter_5
    består av (6) -> TestFilter_5
    <UNFILTERED> -> Junction_57
TestFilter_5
    DEFAULT_VALUE = <UNFILTERED>
    PASSED_TEST_GROUP_OUTPUT = FIRST
    TEST_LIST = "BOOL_OP,OR,COMPOSITE_TEST,""""""1"""""",TEST_CLAUSE,TEST @Value(pav_planfk) = ÄDP",ÄDP,"BOOL_OP,OR,COMPOSITE_TEST,""""""1"""""",TEST_CLAUSE,TEST @Value(pav_planfk) = ÄOB",ÄOB
    ÄDP -> FeatureMerger_10 [SUPPLIER]
    ÄDP -> Junction_57
    ÄOB -> FeatureMerger_10 [SUPPLIER]
    ÄOB -> Junction_57
FeatureMerger_10
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(pb) @Value(pb) AUTO
    LIST_ATTRS_TO_INCLUDE = _pav_akt pb_hanvisn
    LIST_NAME = pav
    MERGE_TYPE = Attributes Only
    PROCESS_DUPS = YES
    REJECT_NULL_MISSING_KEYS = No
    SUPPLIERS_FIRST = No
    MERGED -> ListConcatenator
    UNMERGED_REQUESTOR -> Junction_49
    <REJECTED> -> Junction_50
Junction_50
    -> Junction_52
Junction_57
    -> FeatureMerger_13 [SUPPLIER]
FeatureMerger_13
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(pb) @Value(pb) AUTO
    LIST_ATTRS_TO_INCLUDE = _pav_akt pb_hanvisn
    LIST_NAME = pav
    MERGE_TYPE = Attributes Only
    PROCESS_DUPS = YES
    REJECT_NULL_MISSING_KEYS = No
    SUPPLIERS_FIRST = No
    MERGED -> ListConcatenator
    UNMERGED_REQUESTOR -> Junction_49
    <REJECTED> -> Junction_58
ListConcatenator
    DROP_EMPTY_PARTS = No
    LIST_ATTR = pav{}.pb_hanvisn
    SEP = ,
    VAL_ATTR = pav_p_id
    -> Junction_49
Junction_49
    -> ListConcatenator_2
Note: ListConcatenator_2 [ListConcatenator] / General: / List Attribute: pav{}._pav_akt / Separator Character: / Drop Empty and Null Elements: No / Output Attribute Name: / Destination: pav_akt
ListConcatenator_2
    DROP_EMPTY_PARTS = No
    LIST_ATTR = pav{}._pav_akt
    SEP = "\n"
    VAL_ATTR = pav_akt
    -> ListConcatenator_3
Note: ListConcatenator_3 [ListConcatenator] / General: / List Attribute: pav{}._pav_akt / Separator Character: \n / Drop Empty and Null Elements: No / Output Attribute Name: / Destination: pav_akt_n
ListConcatenator_3
    DROP_EMPTY_PARTS = No
    LIST_ATTR = pav{}._pav_akt
    SEP = \n
    VAL_ATTR = pav_akt_n
    -> ListConcatenator_4
Note: ListConcatenator_4 [ListConcatenator] / General: / List Attribute: pav{}._pav_akt / Separator Character: <br> / Drop Empty and Null Elements: No / Output Attribute Name: / Destination: pav_akt_br
ListConcatenator_4
    DROP_EMPTY_PARTS = No
    LIST_ATTR = pav{}._pav_akt
    SEP = <br>
    VAL_ATTR = pav_akt_br
    -> AttributeRemover
AttributeRemover
    LIST_ATTRS = pav{}
    -> Tester_6
Junction_58
    -> Junction_59
Junction_51
    -> Junction_54

Bookmark: Av ej registrerade beslut kontrollera om plan-id ändå går att erhålla
Note: Måste ha aktbeteckning
Tester_4
    BOOL_OP = OR
    TEST_CLAUSE = TEST lmakt ATTRIBUTE_HAS_A_VALUE ""
    TEST_MODE = TEST
    PASSED -> FeatureMerger_14 [SUPPLIER]
FeatureMerger_14
    ATTR_ACCUM_MODE = Prefix Supplier
    IGNORE_NULLS = No
    JOIN_KEYS = @Value(hanvtext) @Value(lmakt) AUTO
    MERGE_TYPE = Attributes Only
    PROCESS_DUPS = NO
    REJECT_NULL_MISSING_KEYS = No
    SUPPLIERS_FIRST = No
    SUPPLIER_PREFIX = pav_
    MERGED -> AttributeRenamer
    UNMERGED_REQUESTOR -> AttributeCopier

Bookmark: Om planförkortning saknas från register, provar registerkartans typ
Note: Saknar planfk har registerinformation inte lyckats hämtas. / Fallback-klassning av typ från registerkartan. / Överföring av registerkartans beteckning.
AttributeFilter_2
    ATTR_NAME = planfk
    ATTR_VALUES = <Empty>,<Missing>,<Null>,<Unfiltered>
    <EMPTY> -> AttributeValueMapper_3
    <MISSING> -> AttributeValueMapper_3
    <NULL> -> AttributeValueMapper_3
    <UNFILTERED> -> AttributeManager_3
AttributeValueMapper_3
    DEFAULT_VALUE = FME_NULL_VALUE
    DIRECTION = Forward (Source To Destination)
    LUT = PLANBPL,BPL,PLANDP,DP,PLANOB,OB,PLANSPL,SPL,PLANÄDP,ÄDP,PLANTI,TI,PLANFP,FP
    SRC = rk_dep
    VAL_ATTR = planfk
    -> AttributeCopier_2
AttributeCopier_2
    ATTR_TABLE = COPY rk_extid > akt
    MISSING_INPUT_ATTRS = REMOVE
    -> AttributeManager_3

Bookmark: Jämför med ADMSRV0118 och skapar förutsättning för kopiering av avsaknade filer
Note: Plandokument 3rd
FeatureReader_12
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    COMBINE_GEOM = Use Result
    DATASET = $(PlandokumentDir3Rd)
    FORMAT = PATH
    OUTPUT_FEATURES_DISPLAY = Schema and Data Features
    PATH_GLOB_PATTERN = $(PlandokumentFileFilter)
    PATH_NO_EMPTY_PROPERTIES = YES
    PATH_OFFSET_DATETIME = yes
    PATH_RECURSE_DIRECTORIES = NO
    PATH_RETRIEVE_FILE_PROPERTIES = NO
    PATH_TYPE = ANY
    PATH_USE_NON_STRING_ATTR = yes
    PATH -> AttributeManager_5
    <REJECTED> -> Junction_47
AttributeManager_5
    ATTR_TABLE:
      REMOVE path_unix
      RENAME_SET_VALUE path_windows > path_windows_2nd
      REMOVE path_rootname
      RENAME_SET_VALUE path_filename > path_filename_2nd
      RENAME_SET_VALUE path_extension > path_extension_2nd
      REMOVE path_filesize
      REMOVE path_ownername
      REMOVE path_readonly
      REMOVE path_modified_date
      REMOVE path_created_date
      REMOVE path_accessed_date
      REMOVE path_directory_unix
      RENAME_SET_VALUE path_directory_windows > path_directory_windows_2nd
      REMOVE path_type
      REMOVE fme_geometry{}
    -> StringCaseChanger_4
StringCaseChanger_4
    ATTRCHOICE = Selected Attributes
    ATTRLIST = path_directory_windows_2nd path_extension_2nd path_windows_2nd path_filename_2nd
    CHANGE_TYPE = lowercase
    -> Tester_7
Tester_7
    BOOL_OP = OR
    TEST_CLAUSE = TEST @Value(path_extension_2nd) = pdf
    TEST_MODE = TEST
    PASSED -> FeatureMerger_15 [SUPPLIER]
FeatureMerger_15
    ATTR_ACCUM_MODE = Merge Supplier
    ATTR_CONFLICT_RES = Use Requestor
    IGNORE_NULLS = No
    JOIN_KEYS = @Value(path_filename) @Value(path_filename_2nd) AUTO
    MERGE_TYPE = Attributes Only
    PROCESS_DUPS = NO
    REJECT_NULL_MISSING_KEYS = No
    SUPPLIERS_FIRST = No
    UNMERGED_REQUESTOR -> AttributeCreator_2
    UNUSED_SUPPLIER -> AttributeCreator_3
    <REJECTED> -> Junction_47
AttributeCreator_2
    ATTR_TABLE:
      SET_TO filecopy_source_dataset = @Value(path_windows)
      SET_TO filecopy_dest_dataset = $(PlandokumentDir3Rd)/@Value(path_extension)/
      SET_TO filecopy_dest_filename = @Value(path_filename)
    -> AttributeKeeper_5
AttributeKeeper_5
    CREATE_BULK_MODE_FEATURES = No
    KEEP_ATTRS = filecopy_dest_dataset,filecopy_dest_filename,filecopy_source_dataset
    -> Plandokument (output)
AttributeCreator_3
    ATTR_TABLE = SET_TO cmd-command = DEL "@Value(path_windows_2nd)" /Q
    -> Tester_13
Junction_47
    -> Junction_63

Bookmark: Raderar dokument som ej existerar internt
Tester_13
    BOOL_OP = OR
    TEST_CLAUSE:
      TEST @Value(path_windows_2nd) != c:\
      TEST @Value(path_windows_2nd) != d:\
      TEST @Value(path_windows_2nd) != C:\
      TEST @Value(path_windows_2nd) != D:\
      TEST @Value(path_windows_2nd) NOT_CONTAINS *
    TEST_MODE = TEST
    PASSED -> SystemCaller_2
SystemCaller_2
    CMD = @Value(cmd-command)

Bookmark: Bygger "basnamn" baserat på tidigare eller nuvarande aktbeteckning
Tester_akt_egn
    BOOL_OP = OR
    TEST_CLAUSE = TEST @Value(akt_egn) ATTRIBUTE_HAS_VALUE ""
    TEST_MODE = TEST
    PASSED -> AttributeCreator_9
    FAILED -> AttributeCreator_10
AttributeCreator_9
    ATTR_TABLE = SET_TO _basename = @Substring(@Value(akt_egn),6,-1)
    -> StringCaseChanger_3
AttributeCreator_10
    ATTR_TABLE = SET_TO _basename = @ReplaceString(@Value(akt),/,_)
    -> StringCaseChanger_3
StringCaseChanger_3
    ATTRCHOICE = Selected Attributes
    ATTRLIST = _basename
    CHANGE_TYPE = lowercase
    -> StringConcatenator

Bookmark: Bygg filnamn för plandokument: karta, planbeskrivning, genomförandebeskrivning
Note: Karta pdf
StringConcatenator
    ACTION = Create New Attribute
    PARM_LINE = dp@Value(_basename).pdf
    VAL_ATTR = _filpkarta
    -> StringConcatenator_4
Note: Karta tif
StringConcatenator_4
    ACTION = Create New Attribute
    PARM_LINE = dp@Value(_basename).tif
    VAL_ATTR = _filtkarta
    -> StringConcatenator_2
Note: Beskrivning
StringConcatenator_2
    ACTION = Create New Attribute
    PARM_LINE = dp@Value(_basename)_besk.pdf
    VAL_ATTR = _filbesk
    -> StringConcatenator_3
Note: Genomförandebeskrivning
StringConcatenator_3
    ACTION = Create New Attribute
    PARM_LINE = dp@Value(_basename)_genom.pdf
    VAL_ATTR = _filgenom
    -> StringConcatenator_5
Note: Plan- och genomförandebeskrivning
StringConcatenator_5
    ACTION = Create New Attribute
    PARM_LINE = dp@Value(_basename)_pgbesk.pdf
    VAL_ATTR = _filpgbesk
    -> StringConcatenator_6
Note: Bestämmelse
StringConcatenator_6
    ACTION = Create New Attribute
    PARM_LINE = dp@Value(_basename)_best.pdf
    VAL_ATTR = _filbest
    -> StringConcatenator_7
Note: Kvalitetsprogram
StringConcatenator_7
    ACTION = Create New Attribute
    PARM_LINE = dp@Value(_basename)_kvalprog.pdf
    VAL_ATTR = _filkvalprog
    -> FeatureMerger_karta [REQUESTOR]

Bookmark: Karta pdf
FeatureMerger_karta
    ATTR_ACCUM_MODE = Merge Supplier
    ATTR_CONFLICT_RES = Use Requestor
    IGNORE_NULLS = No
    JOIN_KEYS = @Value(_filpkarta) @Value(path_filename) AUTO
    MERGE_TYPE = Attributes Only
    PROCESS_DUPS = NO
    REJECT_NULL_MISSING_KEYS = No
    SUPPLIERS_FIRST = No
    MERGED -> AttributeCreator_12
    UNMERGED_REQUESTOR -> AttributeCreator_13
    UNUSED_SUPPLIER -> FeatureMerger_besk_2 [SUPPLIER]
    <REJECTED> -> Junction_45
AttributeCreator_12
    ATTR_TABLE = SET_TO harpkarta = J
    -> FeatureMerger_besk_2 [REQUESTOR]
AttributeCreator_13
    ATTR_TABLE = SET_TO harpkarta = N
    -> FeatureMerger_besk_2 [REQUESTOR]

Bookmark: Karta tif
FeatureMerger_besk_2
    ATTR_ACCUM_MODE = Merge Supplier
    ATTR_CONFLICT_RES = Use Requestor
    IGNORE_NULLS = No
    JOIN_KEYS = @Value(_filtkarta) @Value(path_filename) AUTO
    MERGE_TYPE = Attributes Only
    PROCESS_DUPS = NO
    REJECT_NULL_MISSING_KEYS = No
    SUPPLIERS_FIRST = No
    MERGED -> AttributeCreator_18
    UNMERGED_REQUESTOR -> AttributeCreator_19
    UNUSED_SUPPLIER -> FeatureMerger_besk [SUPPLIER]
    <REJECTED> -> Junction_45
AttributeCreator_18
    ATTR_TABLE = SET_TO hartkarta = J
    -> FeatureMerger_besk [REQUESTOR]
AttributeCreator_19
    ATTR_TABLE = SET_TO hartkarta = N
    -> FeatureMerger_besk [REQUESTOR]

Bookmark: Beskrivning
FeatureMerger_besk
    ATTR_ACCUM_MODE = Merge Supplier
    ATTR_CONFLICT_RES = Use Requestor
    IGNORE_NULLS = No
    JOIN_KEYS = @Value(_filbesk) @Value(path_filename) AUTO
    MERGE_TYPE = Attributes Only
    PROCESS_DUPS = NO
    REJECT_NULL_MISSING_KEYS = No
    SUPPLIERS_FIRST = No
    MERGED -> AttributeCreator_14
    UNMERGED_REQUESTOR -> AttributeCreator_15
    UNUSED_SUPPLIER -> FeatureMerger_genom [SUPPLIER]
    <REJECTED> -> Junction_45
AttributeCreator_14
    ATTR_TABLE = SET_TO harbesk = J
    -> FeatureMerger_genom [REQUESTOR]
AttributeCreator_15
    ATTR_TABLE = SET_TO harbesk = N
    -> FeatureMerger_genom [REQUESTOR]

Bookmark: Genomförandebeskrivning
FeatureMerger_genom
    ATTR_ACCUM_MODE = Merge Supplier
    ATTR_CONFLICT_RES = Use Requestor
    IGNORE_NULLS = No
    JOIN_KEYS = @Value(_filgenom) @Value(path_filename) AUTO
    MERGE_TYPE = Attributes Only
    PROCESS_DUPS = NO
    REJECT_NULL_MISSING_KEYS = No
    SUPPLIERS_FIRST = No
    MERGED -> AttributeCreator_16
    UNMERGED_REQUESTOR -> AttributeCreator_17
    UNUSED_SUPPLIER -> FeatureMerger_genom_2 [SUPPLIER]
    <REJECTED> -> Junction_45
AttributeCreator_16
    ATTR_TABLE = SET_TO hargenom = J
    -> FeatureMerger_genom_2 [REQUESTOR]
AttributeCreator_17
    ATTR_TABLE = SET_TO hargenom = N
    -> FeatureMerger_genom_2 [REQUESTOR]

Bookmark: Plan- och genomförandebeskrivning
FeatureMerger_genom_2
    ATTR_ACCUM_MODE = Merge Supplier
    ATTR_CONFLICT_RES = Use Requestor
    IGNORE_NULLS = No
    JOIN_KEYS = @Value(_filpgbesk) @Value(path_filename) AUTO
    MERGE_TYPE = Attributes Only
    PROCESS_DUPS = NO
    REJECT_NULL_MISSING_KEYS = No
    SUPPLIERS_FIRST = No
    MERGED -> AttributeCreator_21
    UNMERGED_REQUESTOR -> AttributeCreator_22
    UNUSED_SUPPLIER -> FeatureMerger_genom_3 [SUPPLIER]
    <REJECTED> -> Junction_45
AttributeCreator_21
    ATTR_TABLE = SET_TO harpgbesk = J
    -> FeatureMerger_genom_3 [REQUESTOR]
AttributeCreator_22
    ATTR_TABLE = SET_TO harpgbesk = N
    -> FeatureMerger_genom_3 [REQUESTOR]

Bookmark: Bestämmelse
FeatureMerger_genom_3
    ATTR_ACCUM_MODE = Merge Supplier
    ATTR_CONFLICT_RES = Use Requestor
    IGNORE_NULLS = No
    JOIN_KEYS = @Value(_filbest) @Value(path_filename) AUTO
    MERGE_TYPE = Attributes Only
    PROCESS_DUPS = NO
    REJECT_NULL_MISSING_KEYS = No
    SUPPLIERS_FIRST = No
    MERGED -> AttributeCreator_23
    UNMERGED_REQUESTOR -> AttributeCreator_24
    UNUSED_SUPPLIER -> FeatureMerger_genom_4 [SUPPLIER]
    <REJECTED> -> Junction_45
AttributeCreator_23
    ATTR_TABLE = SET_TO harpbest = J
    -> FeatureMerger_genom_4 [REQUESTOR]
AttributeCreator_24
    ATTR_TABLE = SET_TO harpbest = N
    -> FeatureMerger_genom_4 [REQUESTOR]

Bookmark: Kvalitetsprogram
FeatureMerger_genom_4
    ATTR_ACCUM_MODE = Merge Supplier
    ATTR_CONFLICT_RES = Use Requestor
    IGNORE_NULLS = No
    JOIN_KEYS = @Value(_filkvalprog) @Value(path_filename) AUTO
    MERGE_TYPE = Attributes Only
    PROCESS_DUPS = NO
    REJECT_NULL_MISSING_KEYS = No
    SUPPLIERS_FIRST = No
    MERGED -> AttributeCreator_25
    UNMERGED_REQUESTOR -> AttributeCreator_26
    <REJECTED> -> Junction_45
AttributeCreator_25
    ATTR_TABLE = SET_TO harkvalpro = J
    -> AttributeKeeper_2
AttributeCreator_26
    ATTR_TABLE = SET_TO harkvalpro = N
    -> AttributeKeeper_2

Bookmark: Kolla vilka dokumenttyper som finns för gällande planer
Junction_45
    -> Junction_46

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    INCLUDE_OFFSET = NO
    STAMP_TYPE = datetime
    TIMEZONE = local
    -> DateTimeConverter
DateTimeConverter
    DATETIME_ATTR = _dts
    OUT_FORMAT = %Y-%m-%d %H:%M:%S
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    NO_MATCH = _FME_NO_OP_
    REGEXP = YES
    SRC_ATTRS = _dts
    -> StringReplacer_2
StringReplacer_2
    CASE = NO
    FIND_TEXT = .*\.
    NO_MATCH = _FME_NO_OP_
    REGEXP = YES
    SRC_ATTRS = _mils
    -> SubstringExtractor
SubstringExtractor
    END = 2
    RESULT_ATTR = _subMils
    SRC_STRING = @Value(_mils)
    START = 0
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)

FME custom transformer Fastighet

Parameters:
- RotDirectory = ../   # Katalogen där processen startar
- ProcessModulName =   # Processmodulsnamn
- OutSchemaFileNameSuffix = flush   # Suffix på filnamn för schemalistning (skapas med bindestreck)
- DATASET = @Value(Dataset)   # Dataset
- FME_FEATURE_TYPE_NAME = @Value(fme_feature_type_name)   # Fme Feature Type Name
- FME_FORMAT_SHORT_NAME = @Value(fme_format_short_name)   # Fme Format Short Name
- _FILTERVALUE = @Value(_filterValue)   # Filtervalue

Input (input)
    -> TestFilter_4
TestFilter_4
    DEFAULT_VALUE = <UNFILTERED>
    PASSED_TEST_GROUP_OUTPUT = FIRST
    TEST_LIST = "BOOL_OP,OR,COMPOSITE_TEST,""""""1"""""",TEST_CLAUSE,TEST @Value(_filterValue) = td_drk.rk_fastighet_y",td_drk.rk_fastighet_y,"BOOL_OP,OR,COMPOSITE_TEST,""""""1"""""",TEST_CLAUSE,TEST @Value(_filterValue) = dbo.off_fir_fastigh",dbo.off_fir_fastigh,"BOOL_OP,OR,COMPOSITE_TEST,""""""1"""""",TEST_CLAUSE,TEST @Value(_filterValue) = dbo.off_fir_foratt_status",dbo.off_fir_foratt_status,"BOOL_OP,OR,COMPOSITE_TEST,""""""1"""""",TEST_CLAUSE,TEST @Value(_filterValue) = dbo.fb_fir_lagfart",dbo.fb_fir_lagfart,"BOOL_OP,OR,COMPOSITE_TEST,""""""1"""""",TEST_CLAUSE,TEST @Value(_filterValue) = dbo.tax_taxpers",dbo.tax_taxpers
    td_drk.rk_fastighet_y -> FeatureReader_4 [INITIATOR]
    dbo.off_fir_fastigh -> FeatureReader_5 [INITIATOR]
    dbo.off_fir_foratt_status -> FeatureReader_6 [INITIATOR]
    dbo.fb_fir_lagfart -> FeatureReader_8 [INITIATOR]
    dbo.tax_taxpers -> FeatureReader_9 [INITIATOR]
    <UNFILTERED> -> Junction
FeatureReader_4
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_3
    <REJECTED> -> Junction_11
AttributeExposer_3
    ATTR_LIST = rk_fnr_fr,rk_extid,rk_omrade,rk_dep,rk_objektid
    -> FeatureMerger [REQUESTOR]
Junction_11
    -> Junction_12
Junction_12
    -> <Rejected> (output)
Junction
    -> Junction_2
Junction_2
    -> <Rejected> (output)
Note: Registerpost
FeatureReader_5
    ATTR_ACCUM_MODE = Only Use Result
    COMBINE_GEOM = Use Result
    DATASET = @Value(Dataset)
    FEATURETYPES = @Value(fme_feature_type_name)
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = @Value(Dataset)
    MSSQL_ADO_QUERY_FEATURE_TYPES_FOR_MERGE_FILTERS = Yes
    MSSQL_ADO_READ_CACHE_SIZE = 10
    OUTPUT_FEATURES_DISPLAY = Schema and Data Features
    <OTHER> -> AttributeExposer_4
    <REJECTED> -> Junction_13
AttributeExposer_4
    ATTR_LIST = fnr,status,regenh_r,trakt,fbetnr,UUID
    -> Tester_4
Note: Tester_4 [Tester Version 3] / Test Clauses: LogicLeft ValueOperatorRight Value@Value(status)=L AND @Value(regenh_r)=NAdvanced: / Preserve Feature Order: Across Output Ports
Tester_4
    BOOL_OP = COMPOSITE
    COMPOSITE_TEST = 1 AND 2
    TEST_CLAUSE:
      TEST @Value(status) = L
      TEST @Value(regenh_r) = N
    TEST_MODE = TEST
    PASSED -> FeatureMerger [SUPPLIER]
Note: Unmerged är ej registrerade fastigheter eller samfälligheter / och ska vara med framöver i processen
FeatureMerger
    ATTR_ACCUM_MODE = Merge Supplier
    ATTR_CONFLICT_RES = Use Requestor
    IGNORE_NULLS = No
    JOIN_KEYS = @Value(rk_objektid) @Value(UUID) AUTO
    MERGE_TYPE = Attributes Only
    PROCESS_DUPS = NO
    REJECT_NULL_MISSING_KEYS = No
    SUPPLIERS_FIRST = No
    MERGED -> FeatureMerger_3 [REQUESTOR]
    UNMERGED_REQUESTOR -> AttributeCopier
    <REJECTED> -> Junction_15
AttributeCopier
    ATTR_TABLE = COPY rk_extid > fastighet
    MISSING_INPUT_ATTRS = PRESERVE
    -> FeatureMerger_3 [REQUESTOR]
Junction_15
    -> Junction_16
Junction_16
    -> <Rejected> (output)
Junction_13
    -> Junction_14
Junction_14
    -> <Rejected> (output)
Note: Lagfart
FeatureReader_8
    ATTR_ACCUM_MODE = Only Use Result
    COMBINE_GEOM = Use Result
    DATASET = @Value(Dataset)
    FEATURETYPES = @Value(fme_feature_type_name)
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = @Value(Dataset)
    MSSQL_ADO_QUERY_FEATURE_TYPES_FOR_MERGE_FILTERS = Yes
    MSSQL_ADO_READ_CACHE_SIZE = 10
    OUTPUT_FEATURES_DISPLAY = Schema and Data Features
    <OTHER> -> AttributeExposer_5
    <REJECTED> -> Junction_17
AttributeExposer_5
    ATTR_LIST = FNR,FORVTYP
    -> TestFilter_5
    -> AttributeExposer_7
TestFilter_5
    DEFAULT_VALUE = <UNFILTERED>
    PASSED_TEST_GROUP_OUTPUT = FIRST
    TEST_LIST = BOOL_OP,OR,COMPOSITE_TEST,<Unused>,TEST_CLAUSE,"TEST @Value(FORVTYP) = T",Tomträtt,BOOL_OP,OR,COMPOSITE_TEST,<Unused>,TEST_CLAUSE,"TEST @Value(FORVTYP) = L",Lagfart
    Tomträtt -> Aggregator
    Lagfart -> Aggregator_2
    <UNFILTERED> -> Junction_39
Note: Unmerged är fastigheter utan tomträtt / och ska vara med framöver i processen
FeatureMerger_3
    ATTR_ACCUM_MODE = Merge Supplier
    ATTR_CONFLICT_RES = Use Requestor
    IGNORE_NULLS = No
    JOIN_KEYS = @Value(fnr) @Value(FNR) AUTO
    MERGE_TYPE = Attributes Only
    PROCESS_DUPS = NO
    REJECT_NULL_MISSING_KEYS = No
    SUPPLIERS_FIRST = No
    MERGED -> FeatureMerger_5 [REQUESTOR]
    UNMERGED_REQUESTOR -> AttributeCreator_6
    <REJECTED> -> Junction_19
AttributeCreator_6
    ATTR_TABLE = SET_TO tomtrat = N
    -> FeatureMerger_5 [REQUESTOR]
Junction_19
    -> Junction_20
Junction_20
    -> <Rejected> (output)
Junction_39
    -> Junction_40
Junction_40
    -> <Rejected> (output)
Note: Unmerged är fastigheter utan registrerad lagfart / och ska vara med framöver i processen
FeatureMerger_5
    ATTR_ACCUM_MODE = Merge Supplier
    ATTR_CONFLICT_RES = Use Requestor
    IGNORE_NULLS = No
    JOIN_KEYS = @Value(fnr) @Value(FNR) AUTO
    MERGE_TYPE = Attributes Only
    PROCESS_DUPS = NO
    REJECT_NULL_MISSING_KEYS = No
    SUPPLIERS_FIRST = No
    MERGED -> FeatureMerger_2 [REQUESTOR]
    UNMERGED_REQUESTOR -> AttributeCreator_11
    <REJECTED> -> Junction_21
AttributeCreator_11
    ATTR_TABLE = SET_TO lagfart = N
    -> FeatureMerger_2 [REQUESTOR]
Junction_21
    -> Junction_22
Junction_22
    -> <Rejected> (output)
AttributeExposer_7
    ATTR_LIST = PERSORGNR,NAMN,MELLANNAMN,FORNAMN,EFTERNAMN,TILLT_NAMN
    -> StringCaseChanger
StringCaseChanger
    ATTRCHOICE = Selected Attributes
    ATTRLIST = EFTERNAMN FORNAMN TILLT_NAMN MELLANNAMN NAMN
    CHANGE_TYPE = Full Title Case
    -> Tester_7
Tester_7
    BOOL_OP = OR
    TEST_CLAUSE = TEST @Value(FORNAMN) ATTRIBUTE_HAS_VALUE ""
    TEST_MODE = TEST
    PASSED -> StringConcatenator_2
    FAILED -> TestFilter
StringConcatenator_2
    ACTION = Overwrite Existing Attributes
    ATTRLIST = NAMN
    PARM_LINE = @Value(EFTERNAMN), @Value(FORNAMN)
    -> TestFilter
TestFilter
    DEFAULT_VALUE = <UNFILTERED>
    PASSED_TEST_GROUP_OUTPUT = FIRST
    TEST_LIST = BOOL_OP,OR,COMPOSITE_TEST,<Unused>,TEST_CLAUSE,"TEST @Value(FORVTYP) = L",@Value(FORVTYP) = L,BOOL_OP,OR,COMPOSITE_TEST,<Unused>,TEST_CLAUSE,"TEST @Value(FORVTYP) = T",@Value(FORVTYP) = T
    @Value(FORVTYP) = L -> FeatureMerger_6 [SUPPLIER]
    @Value(FORVTYP) = T -> FeatureMerger_9 [SUPPLIER]
    <UNFILTERED> -> Junction_41
Junction_41
    -> Junction_42
Junction_42
    -> <Rejected> (output)
Junction_17
    -> Junction_18
Junction_18
    -> <Rejected> (output)
Note: Förrättning
FeatureReader_6
    ATTR_ACCUM_MODE = Only Use Result
    COMBINE_GEOM = Use Result
    DATASET = @Value(Dataset)
    FEATURETYPES = @Value(fme_feature_type_name)
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = @Value(Dataset)
    MSSQL_ADO_QUERY_FEATURE_TYPES_FOR_MERGE_FILTERS = Yes
    MSSQL_ADO_READ_CACHE_SIZE = 10
    OUTPUT_FEATURES_DISPLAY = Schema and Data Features
    <OTHER> -> AttributeExposer_6
    <REJECTED> -> Junction_23
AttributeExposer_6
    ATTR_LIST = fnr,flaggnivaa
    -> AttributeCreator_21
AttributeCreator_21
    ATTR_TABLE = SET_TO forratt = J
    -> Tester_5
Note: Tester_5 [Tester Version 3] / Test Clauses: LogicLeft ValueOperatorRight Value@Value(flaggnivaa)=1OR@Value(flaggnivaa)=2Advanced: / Preserve Feature Order: Across Output Ports
Tester_5
    BOOL_OP = OR
    TEST_CLAUSE:
      TEST @Value(flaggnivaa) = 1
      TEST @Value(flaggnivaa) = 2
    TEST_MODE = TEST
    PASSED -> Aggregator_3
Aggregator_3
    ACCUM_ATTRS_NAME = Use Attributes From One Feature
    AGGREGATE_TYPE = Homogeneous Collection (If Possible)
    GROUP_BY = forratt fnr
    MODE = Geometry - Assemble One Level
    SEP = ,
    AGGREGATE -> FeatureMerger_2 [SUPPLIER]
Note: Unmerged är fastigheter utan flagga för förrättning pågår / och ska vara med framöver i processen
FeatureMerger_2
    ATTR_ACCUM_MODE = Merge Supplier
    ATTR_CONFLICT_RES = Use Requestor
    IGNORE_NULLS = No
    JOIN_KEYS = @Value(fnr) @Value(fnr) AUTO
    MERGE_TYPE = Attributes Only
    PROCESS_DUPS = NO
    REJECT_NULL_MISSING_KEYS = No
    SUPPLIERS_FIRST = No
    MERGED -> Tester_6
    UNMERGED_REQUESTOR -> Tester_6
    <REJECTED> -> Junction_25
Tester_6
    BOOL_OP = OR
    TEST_CLAUSE = TEST @Value(forratt) = J
    TEST_MODE = TEST
    PASSED -> Tester_3
    FAILED -> AttributeCreator_16
AttributeCreator_16
    ATTR_TABLE = SET_TO forratt = N
    -> Tester_3
Note: Registrerad eller / oregistrerad
Tester_3
    BOOL_OP = OR
    TEST_CLAUSE:
      TEST fastighet ATTRIBUTE_VALUE_NULL ""
      TEST fastighet ATTRIBUTE_IS_MISSING ""
    TEST_MODE = TEST
    PASSED -> StringConcatenator
    FAILED -> AttributeManager
StringConcatenator
    ACTION = Create New Attribute
    PARM_LINE = fme_basicstring:13%1%14:@Value(trakt) @Value(fbetnr)
    VAL_ATTR = fastighet
    -> AttributeManager
AttributeManager
    ATTR_TABLE:
      RENAME_SET_VALUE fnr > fast_id
      RENAME_SET_VALUE rk_dep > dep
      RENAME_SET_VALUE fbetnr > regnr
      RENAME_SET_VALUE rk_omrade > omrade
      RENAME_SET_VALUE UUID > uuid
      REMOVE rk_fnr_fr
      REMOVE rk_extid
      REMOVE status
      REMOVE regenh_r
      REMOVE FNR
      REMOVE FORVTYP
      REMOVE flaggnivaa
      REMOVE rk_objektid
    -> AttributeExposer
    -> FeatureMerger_6 [REQUESTOR]
    -> Tester_8
    -> Dissolver_2
Note: Lagfaren ägare som Requester för att alla ska få geometri (samma fastighet finns flera gånger). / Vissa lagfarna ägare får ej träff på fastighet, finns bl.a. fastigheter kopplade till andel i outredd / samfällighet. / Krävs geometri för att gå vidare i processen.
FeatureMerger_6
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(fast_id) @Value(FNR) AUTO
    LIST_NAME = owners
    MERGE_TYPE = Attributes and Geometry
    PROCESS_DUPS = YES
    REJECT_NULL_MISSING_KEYS = No
    SUPPLIERS_FIRST = No
    MERGED -> ListExploder
    UNMERGED_REQUESTOR -> FeatureMerger_9 [REQUESTOR]
    <REJECTED> -> Junction_27
ListExploder
    ATTR_ACCUM_MODE = Merge List Attributes
    ATTR_CONFLICT_RES = Use List Attribute Values
    LIST_ATTR = owners{}
    ELEMENTS -> AttributeRenamer_2
    <REJECTED> -> Junction_5
AttributeRenamer_2
    ATTR_TABLE:
      RENAME_SET_DEFAULT EFTERNAMN > L_EFTERNAMN
      RENAME_SET_DEFAULT FORNAMN > L_FORNAMN
      RENAME_SET_DEFAULT MELLANNAMN > L_MELLANNAMN
      RENAME_SET_DEFAULT NAMN > L_NAMN
      RENAME_SET_DEFAULT TILLT_NAMN > L_TILLT_NAMN
      RENAME_SET_DEFAULT PERSORGNR > L_PERSORGNR
    MISSING_INPUT_ATTRS = PRESERVE
    -> FeatureMerger_9 [REQUESTOR]
Note: Tomträttsinnehavare / Geometrin behöver vara drivande för att ej tappa fastigheter
FeatureMerger_9
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(fast_id) @Value(FNR) AUTO
    LIST_NAME = tomtusers
    MERGE_TYPE = Attributes Only
    PROCESS_DUPS = YES
    REJECT_NULL_MISSING_KEYS = No
    SUPPLIERS_FIRST = No
    MERGED -> ListExploder_2
    UNMERGED_REQUESTOR -> FeatureMerger_8 [REQUESTOR]
    <REJECTED> -> Junction_29
ListExploder_2
    ATTR_ACCUM_MODE = Merge List Attributes
    ATTR_CONFLICT_RES = Use List Attribute Values
    LIST_ATTR = tomtusers{}
    ELEMENTS -> AttributeRenamer_3
    <REJECTED> -> Junction_9
AttributeRenamer_3
    ATTR_TABLE:
      RENAME_SET_DEFAULT EFTERNAMN > T_EFTERNAMN
      RENAME_SET_DEFAULT FORNAMN > T_FORNAMN
      RENAME_SET_DEFAULT MELLANNAMN > T_MELLANNAMN
      RENAME_SET_DEFAULT NAMN > T_NAMN
      RENAME_SET_DEFAULT TILLT_NAMN > T_TILLT_NAMN
      RENAME_SET_DEFAULT PERSORGNR > T_PERSORGNR
    MISSING_INPUT_ATTRS = PRESERVE
    -> FeatureMerger_8 [REQUESTOR]
Junction_9
    -> Junction_43
Junction_43
    -> <Rejected> (output)
Junction_29
    -> Junction_30
Junction_30
    -> <Rejected> (output)
Junction_5
    -> Junction_7
Junction_7
    -> <Rejected> (output)
Junction_27
    -> Junction_28
Junction_28
    -> <Rejected> (output)
AttributeExposer
    ATTR_LIST = fme_feature_type_name,fme_feature_type
    -> AttributeCreator_10
    -> Tester
AttributeCreator_10
    ATTR_TABLE:
      SET_TO fme_feature_type_name = fastighet
      SET_TO fme_feature_type = fastighet
    -> Grunddata (output)
Grunddata (output)
Tester
    BOOL_OP = OR
    TEST_CLAUSE = TEST @Value(forratt) = J
    TEST_MODE = TEST
    PASSED -> AttributeCreator_20
AttributeCreator_20
    ATTR_TABLE:
      SET_TO fme_feature_type_name = fastighet
      SET_TO fme_feature_type = fastighet
    -> Forrattning (output)
Forrattning (output)
Junction_25
    -> Junction_26
Junction_26
    -> <Rejected> (output)
Junction_23
    -> Junction_24
Junction_24
    -> <Rejected> (output)
Note: Taxering
FeatureReader_9
    ATTR_ACCUM_MODE = Only Use Result
    COMBINE_GEOM = Use Result
    DATASET = @Value(Dataset)
    FEATURETYPES = @Value(fme_feature_type_name)
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = @Value(Dataset)
    MSSQL_ADO_QUERY_FEATURE_TYPES_FOR_MERGE_FILTERS = Yes
    MSSQL_ADO_READ_CACHE_SIZE = 10
    OUTPUT_FEATURES_DISPLAY = Schema and Data Features
    <OTHER> -> AttributeExposer_8
    <REJECTED> -> Junction_31
AttributeExposer_8
    ATTR_LIST = fnr,persorgnr,taxar
    -> AttributeRenamer_4
AttributeRenamer_4
    ATTR_TABLE = RENAME_SET_DEFAULT PERSORGNR > TAX_PERSORGNR
    MISSING_INPUT_ATTRS = PRESERVE
    -> DateTimeStamper
Junction_31
    -> Junction_32
Junction_32
    -> <Rejected> (output)
Note: Taxerad ägare / Fastighetsgeometrin behöver vara drivande för att ej tappa fastigheter
FeatureMerger_8
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(fast_id) @Value(fnr) AUTO
    LIST_NAME = taxusers
    MERGE_TYPE = Attributes Only
    PROCESS_DUPS = YES
    REJECT_NULL_MISSING_KEYS = No
    SUPPLIERS_FIRST = No
    MERGED -> ListExploder_3
    UNMERGED_REQUESTOR -> AttributeRenamer_5
    <REJECTED> -> Junction_33
ListExploder_3
    ATTR_ACCUM_MODE = Merge List Attributes
    ATTR_CONFLICT_RES = Use List Attribute Values
    LIST_ATTR = taxusers{}
    ELEMENTS -> AttributeRenamer_5
    <REJECTED> -> Junction_44
AttributeRenamer_5
    ATTR_TABLE:
      RENAME_SET_DEFAULT L_EFTERNAMN > l_enamn
      RENAME_SET_DEFAULT L_FORNAMN > l_fnamn
      RENAME_SET_DEFAULT L_MELLANNAMN > l_mnamn
      RENAME_SET_DEFAULT L_NAMN > l_namn
      RENAME_SET_DEFAULT L_PERSORGNR > l_ponr
      RENAME_SET_DEFAULT L_TILLT_NAMN > l_tnamn
      RENAME_SET_DEFAULT T_EFTERNAMN > t_enamn
      RENAME_SET_DEFAULT T_FORNAMN > t_fnamn
      RENAME_SET_DEFAULT T_MELLANNAMN > t_mnamn
      RENAME_SET_DEFAULT T_NAMN > t_namn
      RENAME_SET_DEFAULT T_PERSORGNR > t_ponr
      RENAME_SET_DEFAULT T_TILLT_NAMN > t_tnamn
      RENAME_SET_DEFAULT persorgnr > tx_ponr
      RENAME_SET_DEFAULT taxar > tx_taxar
    MISSING_INPUT_ATTRS = PRESERVE
    -> AttributeKeeper_2
AttributeKeeper_2
    CREATE_BULK_MODE_FEATURES = NO
    KEEP_ATTRS = fastighet,l_enamn,tomtrat,l_mnamn,t_namn,t_fnamn,omrade,tx_ponr,t_enamn,l_fnamn,t_ponr,fast_id,trakt,l_ponr,l_tnamn,forratt,l_namn,tx_taxar,t_tnamn,t_mnamn,lagfart,regnr,dep,uuid
    -> AttributeExposer_2
AttributeExposer_2
    ATTR_LIST = fme_feature_type_name,fme_feature_type
    -> Tester_2
    -> AttributeManager_2
AttributeManager_2
    ATTR_TABLE:
      SET_TO fme_feature_type_name = fastighet
      SET_TO fme_feature_type = fastighet
    -> Agare (output)
Agare (output)
Junction_44
    -> Junction_45
Junction_45
    -> <Rejected> (output)
Junction_33
    -> Junction_34
Junction_34
    -> <Rejected> (output)
Junction_38
    -> <Rejected> (output)
Junction_36
    -> <Rejected> (output)
<Rejected> (output)

Bookmark: Flagga om Tomträtt
Aggregator
    ACCUM_ATTRS_NAME = Use Attributes From One Feature
    AGGREGATE_TYPE = Homogeneous Collection (If Possible)
    GROUP_BY = FNR
    MODE = Geometry - Assemble One Level
    SEP = ,
    AGGREGATE -> AttributeCreator
AttributeCreator
    ATTR_TABLE = SET_TO tomtrat = J
    -> FeatureMerger_3 [SUPPLIER]

Bookmark: Flagga om Lagfart
Aggregator_2
    ACCUM_ATTRS_NAME = Use Attributes From One Feature
    AGGREGATE_TYPE = Homogeneous Collection (If Possible)
    GROUP_BY = FNR
    MODE = Geometry - Assemble One Level
    SEP = ,
    AGGREGATE -> AttributeCreator_7
AttributeCreator_7
    ATTR_TABLE = SET_TO lagfart = J
    -> FeatureMerger_5 [SUPPLIER]

Bookmark: Kommunyta tillverkas
Dissolver_2
    ACCUM_INPUT_ATTRS = Use Attributes From One Feature
    CLEANING_TOLERANCE = Automatic
    CONNECT_Z_MODE = First Wins
    DEAGGREGATE_INPUT = Yes
    AREA -> AttributeManager_3
AttributeManager_3
    ATTR_TABLE:
      REMOVE fast_id
      REMOVE dep
      REMOVE fastighet
      REMOVE trakt
      REMOVE regnr
      REMOVE omrade
      REMOVE lagfart
      REMOVE tomtrat
      REMOVE forratt
      REMOVE uuid
      SET_TO fme_feature_type_name = kommunyta
      SET_TO fme_feature_type = kommunyta
    -> Kommunyta (output)
Kommunyta (output)

Bookmark: Kvarter och trakter tillverkas
Tester_8
    BOOL_OP = OR
    TEST_CLAUSE:
      CASE_INSENSITIVE_TEST @Value(regnr) CONTAINS :
      TEST regnr ATTRIBUTE_VALUE_NULL ""
      TEST regnr ATTRIBUTE_IS_EMPTY ""
      TEST regnr ATTRIBUTE_IS_MISSING ""
    TEST_MODE = TEST
    PASSED -> AttributeCreator_2
    FAILED -> AttributeCreator_3
AttributeCreator_2
    ATTR_TABLE = SET_TO typ = trakt
    -> TestFilter_3
AttributeCreator_3
    ATTR_TABLE = SET_TO typ = kvarter
    -> TestFilter_3
TestFilter_3
    DEFAULT_VALUE = <UNFILTERED>
    PASSED_TEST_GROUP_OUTPUT = FIRST
    TEST_LIST:
      "BOOL_OP,OR,COMPOSITE_TEST,""""""1"""""",TEST_CLAUSE,TEST @Value(dep) = SAMFO",SAMFO,"BOOL_OP,AND,COMPOSITE_TEST,""""""1 AND 2"""""",TEST_CLAUSE,TEST @Value(dep) = FASTO
      CASE_INSENSITIVE_TEST @Value(fastighet) CONTAINS AVAT",FASTO, HAV/VATTEN,"BOOL_OP,OR,COMPOSITE_TEST,""""""1"""""",TEST_CLAUSE,TEST @Value(dep) = FASTO",FASTO, övrigt,"BOOL_OP,OR,COMPOSITE_TEST,""""""1"""""",TEST_CLAUSE,TEST @Value(dep) = SAMF",SAMF,"BOOL_OP,OR,COMPOSITE_TEST,""""""1"""""",TEST_CLAUSE,TEST @Value(dep) = FASTIGHET",FASTIGHET
    SAMFO -> FeatureMerger_4 [REQUESTOR]
    FASTO, HAV/VATTEN -> Junction_4
    FASTO, övrigt -> Junction_4
    SAMF -> FeatureMerger_7 [REQUESTOR]
    FASTIGHET -> AttributeCopier_4
    FASTIGHET -> Aggregator_5
    <UNFILTERED> -> AttributeCopier_4
Note: Bortsorteras / * Det allmänna vattnet (hav) och / * outredda fastigheter, har ingen fastighetsutbredning (ska inte existera i Landskrona)
Junction_4
Dissolver
    ACCUM_INPUT_ATTRS = Use Attributes From One Feature
    CLEANING_TOLERANCE = Automatic
    CONNECT_Z_MODE = First Wins
    DEAGGREGATE_INPUT = Yes
    GROUP_BY = typ namn
    AREA -> Aggregator_4
Aggregator_4
    ACCUM_ATTRS_NAME = Drop Incoming Attributes
    AGGREGATE_TYPE = Homogeneous Collection (If Possible)
    GROUP_BY = namn typ
    MODE = Geometry - Assemble One Level
    SEP = ,
    AGGREGATE -> AttributeManager_4
AttributeManager_4
    ATTR_TABLE:
      RENAME_SET_VALUE namn > namn_vers
      SET_TO fme_feature_type_name = kvarter_och_trakter
      SET_TO fme_feature_type = kvarter_och_trakter
    -> AttributeCopier_2
AttributeCopier_2
    ATTR_TABLE = COPY namn_vers > namn_icap
    MISSING_INPUT_ATTRS = REMOVE
    -> StringCaseChanger_2
StringCaseChanger_2
    ATTRCHOICE = Selected Attributes
    ATTRLIST = namn_icap
    CHANGE_TYPE = Title case
    -> AttributeCopier_3
AttributeCopier_3
    ATTR_TABLE = COPY namn_vers > namn_wcap
    MISSING_INPUT_ATTRS = REMOVE
    -> StringCaseChanger_3
StringCaseChanger_3
    ATTRCHOICE = Selected Attributes
    ATTRLIST = namn_wcap
    CHANGE_TYPE = Full Title Case
    -> Kvarter_Trakter (output)
Kvarter_Trakter (output)

Bookmark: Hanterar om samfällighet ska vara kvarter trots kolon i registernummer
Aggregator_5
    ACCUM_ATTRS_NAME = Drop Incoming Attributes
    AGGREGATE_TYPE = Homogeneous Collection (If Possible)
    GROUP_BY = trakt typ
    MODE = Geometry - Assemble One Level
    SEP = ,
    AGGREGATE -> FeatureMerger_4 [SUPPLIER]
    AGGREGATE -> FeatureMerger_7 [SUPPLIER]
Note: Använder Suppliers typ
FeatureMerger_4
    ATTR_ACCUM_MODE = Merge Supplier
    ATTR_CONFLICT_RES = Use Supplier
    IGNORE_NULLS = No
    JOIN_KEYS = @Value(trakt) @Value(trakt) AUTO
    MERGE_TYPE = Attributes Only
    PROCESS_DUPS = NO
    REJECT_NULL_MISSING_KEYS = No
    SUPPLIERS_FIRST = No
    MERGED -> SubstringExtractor_2
    UNMERGED_REQUESTOR -> SubstringExtractor_2
Note: Använder Suppliers typ
FeatureMerger_7
    ATTR_ACCUM_MODE = Merge Supplier
    ATTR_CONFLICT_RES = Use Supplier
    IGNORE_NULLS = No
    JOIN_KEYS = @Value(trakt) @Value(trakt) AUTO
    MERGE_TYPE = Attributes Only
    PROCESS_DUPS = NO
    REJECT_NULL_MISSING_KEYS = No
    SUPPLIERS_FIRST = No
    MERGED -> AttributeCopier_4
    UNMERGED_REQUESTOR -> AttributeCopier_4

Bookmark: Namn kvarter/trakt
Note: Klipper bort inledande kommunkod och kolon
SubstringExtractor_2
    END = -1
    RESULT_ATTR = _substring
    SRC_STRING = @Value(fastighet)
    START = 5
    -> SubstringExtractor_3
Note: Extraherar kvarters/trakt-namnsdelen
SubstringExtractor_3
    END = @FindString(@Value(_substring),":")-1
    RESULT_ATTR = namn
    SRC_STRING = @Value(_substring)
    START = 0
    -> Dissolver
AttributeCopier_4
    ATTR_TABLE = COPY trakt > namn
    MISSING_INPUT_ATTRS = REMOVE
    -> Dissolver

Bookmark: Hanterar taxeringsår, innevarande år ej är aviserat
DateTimeStamper
    DATETIME_ATTR = _datestamp
    STAMP_TYPE = date
    TIMEZONE = local
    -> SubstringExtractor
SubstringExtractor
    END = 3
    RESULT_ATTR = _yearstamp
    SRC_STRING = @Value(_datestamp)
    START = 0
    -> ExpressionEvaluator
ExpressionEvaluator
    ACTION = Create New Attribute
    EXPRESSION = @Value(_yearstamp)-1
    VAL_ATTR = _yearstampbefore
    -> Tester_9
Tester_9
    BOOL_OP = OR
    TEST_CLAUSE = TEST @Value(taxar) >= @Value(_yearstampbefore)
    TEST_MODE = TEST
    PASSED -> TestFilter_2
TestFilter_2
    DEFAULT_VALUE = <UNFILTERED>
    PASSED_TEST_GROUP_OUTPUT = FIRST
    TEST_LIST = "BOOL_OP,AND,COMPOSITE_TEST,""""""1"""""",TEST_CLAUSE,TEST @Value(taxar) = @Value(_yearstamp)",@Value(taxar) = @Value(_yearstamp),"BOOL_OP,AND,COMPOSITE_TEST,""""""1"""""",TEST_CLAUSE,TEST @Value(taxar) = @Value(_yearstampbefore)",@Value(taxar) = @Value(_yearstampbefore)
    @Value(taxar) = @Value(_yearstamp) -> FeatureMerger_10 [SUPPLIER]
    @Value(taxar) = @Value(_yearstampbefore) -> FeatureMerger_11 [SUPPLIER]
Creator
    GEOMTYPE = Geometry Object
    NUM = 1
    CREATED -> FeatureMerger_10 [REQUESTOR]
Note: Innevarande år
FeatureMerger_10
    ATTR_ACCUM_MODE = Merge Supplier
    ATTR_CONFLICT_RES = Use Supplier
    CLEANING_TOLERANCE = None
    CONNECT_Z_MODE = First Wins
    GEOM_TYPE = Build Polygons
    IGNORE_NULLS = No
    JOIN_KEYS = 1 1 AUTO
    MERGE_TYPE = Attributes and Geometry
    PROCESS_DUPS = YES
    REJECT_NULL_MISSING_KEYS = No
    SUPPLIERS_FIRST = No
    UNMERGED_REQUESTOR -> FeatureMerger_11 [REQUESTOR]
    USED_SUPPLIER -> Junction_3
    <REJECTED> -> Junction_35
Note: Föregående år
FeatureMerger_11
    ATTR_ACCUM_MODE = Merge Supplier
    ATTR_CONFLICT_RES = Use Supplier
    CLEANING_TOLERANCE = None
    CONNECT_Z_MODE = First Wins
    GEOM_TYPE = Build Polygons
    IGNORE_NULLS = No
    JOIN_KEYS = 1 1 AUTO
    MERGE_TYPE = Attributes and Geometry
    PROCESS_DUPS = YES
    REJECT_NULL_MISSING_KEYS = No
    SUPPLIERS_FIRST = No
    USED_SUPPLIER -> Junction_3
    <REJECTED> -> Junction_37
Junction_3
    -> FeatureMerger_8 [SUPPLIER]
Junction_37
    -> Junction_38
Junction_35
    -> Junction_36

Bookmark: Landskrona stad
Note: Tester_2 [Tester Version 3] / Test Clauses: LogicLeft ValueOperatorRight Value@Value(l_ponr)=16212000-1140 OR (( @Value(l_ponr)Attribute Is Null OR @Value(l_ponr)Attribute Is Missing ) AND @Value(tx_ponr)=16212000-1140 )Advanced: / Preserve Feature Order: Across Output Ports
Tester_2
    BOOL_OP = COMPOSITE
    COMPOSITE_TEST = 1 OR (( 2 OR 3 ) AND 4 )
    TEST_CLAUSE:
      TEST @Value(l_ponr) = 16212000-1140
      TEST l_ponr ATTRIBUTE_VALUE_NULL ""
      TEST l_ponr ATTRIBUTE_IS_MISSING ""
      TEST @Value(tx_ponr) = 16212000-1140
    TEST_MODE = TEST
    PASSED -> Matcher
Note: Unik
Matcher
    BLANK_AND_MISSING_DIFFER = No
    CHECK_COORDINATE_SYSTEMS = No
    CHECK_TYPES_AND_ENCODINGS = No
    CNT_ATTR = _match_id
    LENIENT_MATCH = No
    MATCH = 2D
    MATCH_STRATEGY = Match All Attributes
    SINGLE_MATCHED -> AttributeRemover_3
    NOT_MATCHED -> AttributeRemover_3
AttributeRemover_3
    REMOVE_ATTRS = _match_id
    -> AttributeCreator_13
AttributeCreator_13
    ATTR_TABLE:
      SET_TO fme_feature_type_name = fastighet
      SET_TO fme_feature_type = fastighet
    -> Landskrona_stad (output)
    -> TestFilter_lagfag_taxag
Landskrona_stad (output)
Note: TestFilter_lagfag_taxag
TestFilter_lagfag_taxag
    DEFAULT_VALUE = <UNFILTERED>
    PASSED_TEST_GROUP_OUTPUT = FIRST
    TEST_LIST:
      BOOL_OP,OR,COMPOSITE_TEST,<Unused>,TEST_CLAUSE,"TEST @Value(l_ponr) = 16212000-1140",lkra stad lagfag,BOOL_OP,COMPOSITE,COMPOSITE_TEST,"""(1 OR 2) AND 3""",TEST_CLAUSE,"TEST l_ponr ATTRIBUTE_VALUE_NULL """"
      TEST l_ponr ATTRIBUTE_IS_MISSING """"
      TEST @Value(tx_ponr) = 16212000-1140",lkra stad taxag
    lkra stad lagfag -> Tester_TOMTR
    lkra stad lagfag -> Matcher_2
    lkra stad taxag -> Matcher_5
Matcher_2
    BLANK_AND_MISSING_DIFFER = No
    CHECK_COORDINATE_SYSTEMS = No
    CHECK_TYPES_AND_ENCODINGS = No
    CNT_ATTR = _match_id
    LENIENT_MATCH = No
    MATCH = 2D
    MATCHATTRS = fastighet tomtrat
    MATCH_STRATEGY = Match Selected Attributes
    SINGLE_MATCHED -> Landskrona_stad_lagfart (output)
    NOT_MATCHED -> Landskrona_stad_lagfart (output)
Landskrona_stad_lagfart (output)
Tester_TOMTR
    BOOL_OP = OR
    TEST_CLAUSE = TEST @Value(tomtrat) = J
    TEST_MODE = TEST
    PASSED -> Matcher_3
    FAILED -> Matcher_4
Matcher_3
    BLANK_AND_MISSING_DIFFER = No
    CHECK_COORDINATE_SYSTEMS = No
    CHECK_TYPES_AND_ENCODINGS = No
    CNT_ATTR = _match_id
    LENIENT_MATCH = No
    MATCH = 2D
    MATCHATTRS = fastighet tomtrat
    MATCH_STRATEGY = Match Selected Attributes
    SINGLE_MATCHED -> Landskrona_stad_lagfart_tomtratt (output)
    NOT_MATCHED -> Landskrona_stad_lagfart_tomtratt (output)
Landskrona_stad_lagfart_tomtratt (output)
Matcher_4
    BLANK_AND_MISSING_DIFFER = No
    CHECK_COORDINATE_SYSTEMS = No
    CHECK_TYPES_AND_ENCODINGS = No
    CNT_ATTR = _match_id
    LENIENT_MATCH = No
    MATCH = 2D
    MATCHATTRS = fastighet tomtrat
    MATCH_STRATEGY = Match Selected Attributes
    SINGLE_MATCHED -> Landskrona_stad_lagfart_ej_tomtratt (output)
    NOT_MATCHED -> Landskrona_stad_lagfart_ej_tomtratt (output)
Landskrona_stad_lagfart_ej_tomtratt (output)
Matcher_5
    BLANK_AND_MISSING_DIFFER = No
    CHECK_COORDINATE_SYSTEMS = No
    CHECK_TYPES_AND_ENCODINGS = No
    CNT_ATTR = _match_id
    LENIENT_MATCH = No
    MATCH = 2D
    MATCHATTRS = fastighet tomtrat
    MATCH_STRATEGY = Match Selected Attributes
    SINGLE_MATCHED -> Landskrona_stad_lagfart_taxering (output)
    NOT_MATCHED -> Landskrona_stad_lagfart_taxering (output)
Landskrona_stad_lagfart_taxering (output)

FME custom transformer DateHandler

Parameters:
- _DATUM = @Value(_datum)   # Datum
- _OWERWRITE = Nej   # Skriv över
- _ATTRIBUT =   # " " Målattribut

Input (input)
    -> Tester_3
Tester_3
    BOOL_OP = OR
    TEST_CLAUSE = TEST _datum NOT_ATTRIBUTE_VALUE_NULL ""
    TEST_MODE = TEST
    PASSED -> Tester_2
    FAILED -> Tester
Tester_2
    BOOL_OP = OR
    TEST_CLAUSE = TEST @Value(_datum) CONTAINS_REGEX ^(18|19|20|21)\d\d(0[1-9]|1[012])(0[1-9]|[12][0-9]|3[01])$
    TEST_MODE = TEST
    PASSED -> DateTimeConverter
    FAILED -> AttributeCreator
DateTimeConverter
    DATETIME_ATTR = _datum
    IN_FORMAT = %Y%m%d$
    OUT_FORMAT = %Y-%m-%d
    PASSTHROUGH = NO
    REPAIR_INPUT = NO
    -> Tester
    <REJECTED> -> <Rejected> (output)
<Rejected> (output)
AttributeCreator
    ATTR_TABLE = SET_TO _datum = FME_NULL_VALUE
    -> Tester
Tester
    BOOL_OP = OR
    TEST_CLAUSE = TEST $(_OWERWRITE) = Ja
    TEST_MODE = TEST
    PASSED -> AttributeCreator_2
    FAILED -> Output (output)
AttributeCreator_2
    ATTR_TABLE = SET_TO $(_ATTRIBUT) = @Value(_datum)
    -> Output (output)
Output (output)

FME custom transformer Gemensamhetsanlaggning

Parameters:
- RotDirectory = ../   # Katalogen där processen startar
- ProcessModulName =   # Processmodulsnamn
- OutSchemaFileNameSuffix = flush   # Suffix på filnamn för schemalistning (skapas med bindestreck)
- _FILTERVALUE = @Value(_filterValue)   # Filtervalue
- DATASET = @Value(Dataset)   # Dataset
- FME_FEATURE_TYPE_NAME = @Value(fme_feature_type_name)   # Fme Feature Type Name
- FME_FORMAT_SHORT_NAME = @Value(fme_format_short_name)   # Fme Format Short Name

Input (input)
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(_filterValue) = td_drk.rk_ga_l",td_drk.rk_ga_l,"BOOL_OP,OR,COMPOSITE_TEST,""""""1"""""",TEST_CLAUSE,TEST @Value(_filterValue) = td_drk.rk_ga_p",td_drk.rk_ga_p,"BOOL_OP,OR,COMPOSITE_TEST,""""""1"""""",TEST_CLAUSE,TEST @Value(_filterValue) = td_drk.rk_ga_y",td_drk.rk_ga_y,"BOOL_OP,OR,COMPOSITE_TEST,""""""1"""""",TEST_CLAUSE,TEST @Value(_filterValue) = dbo.off_fir_andamal",dbo.off_fir_andamal
    td_drk.rk_ga_l -> FeatureReader_4 [INITIATOR]
    td_drk.rk_ga_p -> FeatureReader_2 [INITIATOR]
    td_drk.rk_ga_y -> FeatureReader_3 [INITIATOR]
    dbo.off_fir_andamal -> FeatureReader_8 [INITIATOR]
FeatureReader_4
    ATTR_ACCUM_MODE = Merge Initiator and Result
    ATTR_CONFLICT_RES = Use Result
    ATTR_IGNORE_NULLS = No
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer
    <REJECTED> -> Junction_11
AttributeExposer
    ATTR_LIST = rk_fnr,rk_fnr_fr,rk_dep,rk_extid,rk_kommun,rk_trakt,rk_block_enhet,rk_fastighet
    -> FeatureMerger_9 [REQUESTOR]
Junction_11
    -> <Rejected> (output)
FeatureReader_2
    ATTR_ACCUM_MODE = Merge Initiator and Result
    ATTR_CONFLICT_RES = Use Result
    ATTR_IGNORE_NULLS = No
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_2
    <REJECTED> -> Junction_2
AttributeExposer_2
    ATTR_LIST = rk_fnr,rk_fnr_fr,rk_dep,rk_extid,rk_kommun,rk_trakt,rk_block_enhet,rk_fastighet
    -> FeatureMerger_2 [REQUESTOR]
Junction_2
    -> <Rejected> (output)
FeatureReader_3
    ATTR_ACCUM_MODE = Merge Initiator and Result
    ATTR_CONFLICT_RES = Use Result
    ATTR_IGNORE_NULLS = No
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_3
    <REJECTED> -> Junction_3
AttributeExposer_3
    ATTR_LIST = rk_fnr,rk_fnr_fr,rk_dep,rk_extid,rk_kommun,rk_trakt,rk_block_enhet,rk_fastighet
    -> FeatureMerger_3 [REQUESTOR]
Junction_3
    -> <Rejected> (output)
FeatureReader_8
    ATTR_ACCUM_MODE = Only Use Result
    COMBINE_GEOM = Use Result
    DATASET = @Value(Dataset)
    FEATURETYPES = @Value(fme_feature_type_name)
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = @Value(Dataset)
    MSSQL_ADO_QUERY_FEATURE_TYPES_FOR_MERGE_FILTERS = Yes
    MSSQL_ADO_READ_CACHE_SIZE = 10
    OUTPUT_FEATURES_DISPLAY = Schema and Data Features
    <OTHER> -> AttributeExposer_4
    <REJECTED> -> Junction_17
AttributeExposer_4
    ATTR_LIST = gsfnr,amaltext
    -> FeatureMerger_9 [SUPPLIER]
    -> FeatureMerger_2 [SUPPLIER]
    -> FeatureMerger_3 [SUPPLIER]
FeatureMerger_9
    ATTR_ACCUM_MODE = Merge Supplier
    ATTR_CONFLICT_RES = Use Requestor
    IGNORE_NULLS = No
    JOIN_KEYS = @Value(rk_fnr_fr) @Value(gsfnr) AUTO
    MERGE_TYPE = Attributes Only
    PROCESS_DUPS = NO
    REJECT_NULL_MISSING_KEYS = No
    SUPPLIERS_FIRST = No
    MERGED -> Linje (output)
    UNMERGED_REQUESTOR -> Linje (output)
    <REJECTED> -> <Rejected> (output)
Linje (output)
FeatureMerger_2
    ATTR_ACCUM_MODE = Merge Supplier
    ATTR_CONFLICT_RES = Use Requestor
    IGNORE_NULLS = No
    JOIN_KEYS = @Value(rk_fnr_fr) @Value(gsfnr) AUTO
    MERGE_TYPE = Attributes Only
    PROCESS_DUPS = NO
    REJECT_NULL_MISSING_KEYS = No
    SUPPLIERS_FIRST = No
    MERGED -> Punkt (output)
    UNMERGED_REQUESTOR -> Punkt (output)
    <REJECTED> -> <Rejected> (output)
Punkt (output)
FeatureMerger_3
    ATTR_ACCUM_MODE = Merge Supplier
    ATTR_CONFLICT_RES = Use Requestor
    IGNORE_NULLS = No
    JOIN_KEYS = @Value(rk_fnr_fr) @Value(gsfnr) AUTO
    MERGE_TYPE = Attributes Only
    PROCESS_DUPS = NO
    REJECT_NULL_MISSING_KEYS = No
    SUPPLIERS_FIRST = No
    MERGED -> Yta (output)
    UNMERGED_REQUESTOR -> Yta (output)
    <REJECTED> -> <Rejected> (output)
Yta (output)
Junction_17
    -> <Rejected> (output)
<Rejected> (output)

FME custom transformer ConcatenatedSample

Parameters:
- FME_DATASET = @Value(fme_dataset)   # Attribute to Sample Concatenate
- NumberToShorten = 3   # Antal innan förkortning

StringAttribute (input)
    -> Aggregator
Aggregator
    ACCUM_ATTRS_NAME = Use Attributes From One Feature
    AGGREGATE_TYPE = Homogeneous Collection (If Possible)
    COUNT_ATTR = TotaltAntal
    LIST_ATTRS_TO_INCLUDE = fme_dataset
    LIST_NAME = dataset
    MODE = Geometry - Assemble One Level
    ORDERED = No
    SEP = ,
    AGGREGATE -> Tester_2
Tester_2
    BOOL_OP = OR
    TEST_CLAUSE = TEST @Value(TotaltAntal) > 3
    TEST_MODE = TEST
    PASSED -> ListIndexer
    FAILED -> ListConcatenator
ListIndexer
    INDEX = 0
    LIST_ATTR = dataset{}
    PREFIX = _ds0_
    -> ListIndexer_2
ListIndexer_2
    INDEX = 1
    LIST_ATTR = dataset{}
    PREFIX = _ds1_
    -> ListIndexer_3
ListIndexer_3
    INDEX = @Value(TotaltAntal)-1
    LIST_ATTR = dataset{}
    PREFIX = _dsn_
    -> StringConcatenator
StringConcatenator
    ACTION = Create New Attribute
    PARM_LINE = @Value(_ds0_fme_dataset), @Value(_ds1_fme_dataset), ... , @Value(_dsn_fme_dataset)
    VAL_ATTR = fme_dataset_concatenated
    -> StringConcatenator_OUTPUT_-__StringConcatenator_Output
ListConcatenator
    DROP_EMPTY_PARTS = No
    LIST_ATTR = dataset{}.fme_dataset
    SEP = ", "
    VAL_ATTR = fme_dataset_concatenated
    -> StringConcatenator_OUTPUT_-__StringConcatenator_Output
StringConcatenator_OUTPUT_-__StringConcatenator_Output: Junction
    -> AttributeRemover
AttributeRemover
    LIST_ATTRS = dataset{} dataset{}.fme_dataset
    REMOVE_ATTRS = fme_dataset,_ds1_fme_dataset,_dsn_fme_dataset,dataset{0}.fme_dataset,_ds0_fme_dataset
    -> StringConcatenatedSample (output)
StringConcatenatedSample (output)

FME custom transformer SearchBoundingBoxAndPoint

Parameters:
- ATTRIBUTES =   # "" Select Attribute Names

Input (input)
    -> AttributeExposer_2
AttributeExposer_2
    ATTR_LIST = fme_type
    -> TestFilter_5
Note: yta linje eller punkt
TestFilter_5
    DEFAULT_VALUE = <UNFILTERED>
    PASSED_TEST_GROUP_OUTPUT = FIRST
    TEST_LIST = BOOL_OP,OR,COMPOSITE_TEST,<Unused>,TEST_CLAUSE,"TEST @Value(fme_type) = fme_area",area,BOOL_OP,OR,COMPOSITE_TEST,<Unused>,TEST_CLAUSE,"TEST @Value(fme_type) = fme_line",line,"BOOL_OP,OR,COMPOSITE_TEST,""""""1"""""",TEST_CLAUSE,TEST @Value(fme_type) = fme_point",point
    area -> CenterPointReplacer
    area -> Aggregator_4
    line -> Snipper
    line -> Aggregator_4
    point -> Bufferer
    point -> Junction_5
    <UNFILTERED> -> StringConcatenator
BoundingBox (output)
point (output)
<Rejected> (output)

Bookmark: Sökunderlag yta
Bufferer
    ANGLE = 22.5
    CAP_STYLE = Arc
    CORNER_STYLE = Arc
    MODE = AREA
    OFFSET = 1
    OFFSET_UNITS = NONE
    PRECISION = APPROX
    BUFFERED -> Aggregator_4
    <REJECTED> -> Aggregator
Aggregator_4
    ACCUM_ATTRS_NAME = Use Attributes From One Feature
    AGGREGATE_TYPE = Homogeneous Collection (If Possible)
    GROUP_BY = $(ATTRIBUTES)
    MODE = Geometry - Assemble One Level
    SEP = ,
    AGGREGATE -> BoundingBoxReplacer
BoundingBoxReplacer
    BOXTYPE = 2D Bounding Box
    BOX -> BoundingBox (output)

Bookmark: Sökunderlag punkt
Note: Sökpunkt representation yta
CenterPointReplacer
    POINTTYPE = INSIDE
    POINT -> Junction_5
    UNTOUCHED -> Aggregator
Note: Sökpunkt representation linje
Snipper
    DEAGGREGATE_INPUT = YES
    ENDLOCATIONATTR = 50
    MEASUREMENTTYPE = 2D
    SNIPMODE = Distance (Percentage)
    STARTLOCATIONATTR = 50
    -> Junction_5
    <REJECTED> -> Aggregator
Junction_5
    -> Aggregator_5
Aggregator_5
    ACCUM_ATTRS_NAME = Use Attributes From One Feature
    AGGREGATE_TYPE = Homogeneous Collection (If Possible)
    GROUP_BY = $(ATTRIBUTES)
    MODE = Geometry - Assemble One Level
    SEP = ,
    AGGREGATE -> point (output)

Bookmark: Felmeddelande homogeniserad till en post
Aggregator
    ACCUM_ATTRS_NAME = Use Attributes From One Feature
    AGGREGATE_TYPE = Homogeneous Collection (If Possible)
    GROUP_BY = fme_rejection_code
    MODE = Geometry - Assemble One Level
    SEP = ,
    AGGREGATE -> AttributeRenamer
AttributeRenamer
    ATTR_TABLE = RENAME_SET_DEFAULT fme_rejection_code > error_msg
    MISSING_INPUT_ATTRS = REMOVE
    -> Aggregator_3
StringConcatenator
    ACTION = Create New Attribute
    PARM_LINE = fme_basicstring:19%16%55:Följande fme_type '@Value(fme_type)' hanterades inte men förekom. Ställningstagande krävs.
    VAL_ATTR = error_msg
    -> Aggregator_2
Aggregator_2
    ACCUM_ATTRS_NAME = Use Attributes From One Feature
    AGGREGATE_TYPE = Homogeneous Collection (If Possible)
    GROUP_BY = error_msg
    MODE = Geometry - Assemble One Level
    SEP = ,
    AGGREGATE -> Aggregator_3
Aggregator_3
    ACCUM_ATTRS_NAME = Use Attributes From One Feature
    AGGREGATE_TYPE = Homogeneous Collection (If Possible)
    GROUP_BY = error_msg
    MODE = Geometry - Assemble One Level
    SEP = ,
    AGGREGATE -> ListBuilder
ListBuilder
    LIST_ATTRS_TO_INCLUDE = error_msg
    LIST_NAME = _error_msgs
    -> ListConcatenator
ListConcatenator
    DROP_EMPTY_PARTS = Yes
    LIST_ATTR = _error_msgs{}.error_msg
    SEP = "\n"
    VAL_ATTR = error_msg
    -> <Rejected> (output)

FME custom transformer Rattighet

Parameters:
- RotDirectory = ../   # Katalogen där processen startar
- ProcessModulName =   # Processmodulsnamn
- OutSchemaFileNameSuffix = flush   # Suffix på filnamn för schemalistning (skapas med bindestreck)
- _FILTERVALUE = @Value(_filterValue)   # Filtervalue
- DATASET = @Value(Dataset)   # Dataset
- FME_FEATURE_TYPE_NAME = @Value(fme_feature_type_name)   # Fme Feature Type Name
- FME_FORMAT_SHORT_NAME = @Value(fme_format_short_name)   # Fme Format Short Name

Input (input)
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(_filterValue) = td_drk.rk_rattighet_l",td_drk.rk_rattighet_l,"BOOL_OP,OR,COMPOSITE_TEST,""""""1"""""",TEST_CLAUSE,TEST @Value(_filterValue) = td_drk.rk_rattighet_p",td_drk.rk_rattighet_p,"BOOL_OP,OR,COMPOSITE_TEST,""""""1"""""",TEST_CLAUSE,TEST @Value(_filterValue) = td_drk.rk_rattighet_y",td_drk.rk_rattighet_y,"BOOL_OP,OR,COMPOSITE_TEST,""""""1"""""",TEST_CLAUSE,TEST @Value(_filterValue) = dbo.off_fir_rattigh",dbo.off_fir_rattigh
    td_drk.rk_rattighet_l -> FeatureReader_4 [INITIATOR]
    td_drk.rk_rattighet_p -> FeatureReader_2 [INITIATOR]
    td_drk.rk_rattighet_y -> FeatureReader_3 [INITIATOR]
    dbo.off_fir_rattigh -> FeatureReader_8 [INITIATOR]
FeatureReader_4
    ATTR_ACCUM_MODE = Merge Initiator and Result
    ATTR_CONFLICT_RES = Use Result
    ATTR_IGNORE_NULLS = No
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer
    <REJECTED> -> Junction_11
AttributeExposer
    ATTR_LIST = rk_fnr,rk_dep,rk_extid,rk_gdat,rk_adat,rk_xyfel
    -> BulkAttributeRenamer
BulkAttributeRenamer
    ATTRCHOICE = All Attributes
    CASE_DISP = NO
    MODE_CHOICE = RENAME
    PATTERN_ACTION_DISP = REMOVEPREFIX
    REPLACE_STR = rk_
    -> FeatureMerger_7 [REQUESTOR]
Junction_11
    -> <Rejected> (output)
FeatureReader_2
    ATTR_ACCUM_MODE = Merge Initiator and Result
    ATTR_CONFLICT_RES = Use Result
    ATTR_IGNORE_NULLS = No
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_2
    <REJECTED> -> Junction_2
AttributeExposer_2
    ATTR_LIST = rk_fnr,rk_dep,rk_extid,rk_gdat,rk_adat,rk_xyfel
    -> BulkAttributeRenamer_2
BulkAttributeRenamer_2
    ATTRCHOICE = All Attributes
    CASE_DISP = NO
    MODE_CHOICE = RENAME
    PATTERN_ACTION_DISP = REMOVEPREFIX
    REPLACE_STR = rk_
    -> FeatureMerger_2 [REQUESTOR]
Junction_2
    -> <Rejected> (output)
FeatureReader_3
    ATTR_ACCUM_MODE = Merge Initiator and Result
    ATTR_CONFLICT_RES = Use Result
    ATTR_IGNORE_NULLS = No
    COMBINE_GEOM = Use Result
    DATASET = @Value(Dataset)
    FEATURETYPES = @Value(fme_feature_type_name)
    FORMAT = POSTGIS
    INTERACT = NONE
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_3
    <REJECTED> -> Junction_3
AttributeExposer_3
    ATTR_LIST = rk_fnr,rk_dep,rk_extid,rk_gdat,rk_adat,rk_xyfel
    -> BulkAttributeRenamer_3
BulkAttributeRenamer_3
    ATTRCHOICE = All Attributes
    CASE_DISP = NO
    MODE_CHOICE = RENAME
    PATTERN_ACTION_DISP = REMOVEPREFIX
    REPLACE_STR = rk_
    -> FeatureMerger_3 [REQUESTOR]
Junction_3
    -> <Rejected> (output)
FeatureReader_8
    ATTR_ACCUM_MODE = Only Use Result
    COMBINE_GEOM = Use Result
    DATASET = @Value(Dataset)
    FEATURETYPES = @Value(fme_feature_type_name)
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = @Value(Dataset)
    MSSQL_ADO_QUERY_FEATURE_TYPES_FOR_MERGE_FILTERS = Yes
    MSSQL_ADO_READ_CACHE_SIZE = 10
    OUTPUT_FEATURES_DISPLAY = Schema and Data Features
    <OTHER> -> AttributeExposer_4
    <REJECTED> -> Junction_17
AttributeExposer_4
    ATTR_LIST = lmv_deleted,lankod,aktbet,rattighnr,rtyp,rstatus,rajour,ej_rattutredd,randamal,atgard,atgarddat,sen_andr_dat,rperanm,ranm,rbesk,UUID,RFASTTILLBEHOR
    -> Tester
Tester
    BOOL_OP = OR
    TEST_CLAUSE = TEST @Value(lmv_deleted) = N
    TEST_MODE = TEST
    PASSED -> StringConcatenator
StringConcatenator
    ACTION = Create New Attribute
    PARM_LINE = fme_basicstring:14%1%17:@Value(aktbet).@Value(rattighnr)
    VAL_ATTR = aktbet_hela
    -> BulkAttributeRenamer_4
BulkAttributeRenamer_4
    ATTRCHOICE = All Attributes
    CASE_CHANGE_TYPE = lower
    MODE_CHOICE = RENAME
    PATTERN_ACTION_DISP = CASECHANGE
    -> FeatureMerger_3 [SUPPLIER]
    -> FeatureMerger_7 [SUPPLIER]
    -> FeatureMerger_2 [SUPPLIER]
FeatureMerger_7
    ATTR_ACCUM_MODE = Merge Supplier
    ATTR_CONFLICT_RES = Use Requestor
    IGNORE_NULLS = No
    JOIN_KEYS = @Value(extid) @Value(aktbet_hela) AUTO
    MERGE_TYPE = Attributes Only
    PROCESS_DUPS = NO
    REJECT_NULL_MISSING_KEYS = No
    SUPPLIERS_FIRST = No
    MERGED -> Linje (output)
    UNMERGED_REQUESTOR -> Linje (output)
    <REJECTED> -> <Rejected> (output)
Linje (output)
FeatureMerger_2
    ATTR_ACCUM_MODE = Merge Supplier
    ATTR_CONFLICT_RES = Use Requestor
    IGNORE_NULLS = No
    JOIN_KEYS = @Value(extid) @Value(aktbet_hela) AUTO
    MERGE_TYPE = Attributes Only
    PROCESS_DUPS = NO
    REJECT_NULL_MISSING_KEYS = No
    SUPPLIERS_FIRST = No
    MERGED -> Punkt (output)
    UNMERGED_REQUESTOR -> Punkt (output)
    <REJECTED> -> <Rejected> (output)
Punkt (output)
FeatureMerger_3
    ATTR_ACCUM_MODE = Merge Supplier
    ATTR_CONFLICT_RES = Use Requestor
    IGNORE_NULLS = No
    JOIN_KEYS = @Value(extid) @Value(aktbet_hela) AUTO
    MERGE_TYPE = Attributes Only
    PROCESS_DUPS = NO
    REJECT_NULL_MISSING_KEYS = No
    SUPPLIERS_FIRST = No
    MERGED -> Yta (output)
    UNMERGED_REQUESTOR -> Yta (output)
    <REJECTED> -> <Rejected> (output)
Yta (output)
Junction_17
    -> <Rejected> (output)
<Rejected> (output)
