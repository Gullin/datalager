FME workspace postgis-td_baskarta_anpassat_markdetaljtyp-DatalagerManage-main-POSTGIS.fmw

Parameters:
- RotDirectory = ../   # Katalogen där processen startar
- ProcessName =   # Processnamn
- OutputDirectory = C:\LKR_GIS\Datalager_procsrc\_geodatarepo\landskrona\lkr_gis   # Katalog för lagring av del av datalager
- ProcessModulName =   # Processmodulsnamn
- IsWholeProcessRun = 1   # Är hela datalagerprocessen körd
- Manifest = $(RotDirectory)$(ProcessModulName)/_schema/schema-manifest.xlsx   # Manifest (export- och schema-specifikation)
- SchemaFlush = $(RotDirectory)$(ProcessModulName)/_schema/schema-flush.xlsx   # Schemaspecifikation för aktuellt data
- DatabaseSchema = LKR_GIS   # Databasschema (ska vara samma som anslutningsnamnet i FME)
- PG_SCHEMA =   # PostgreSQL Schema
- Datatable =
- DestDataset_POSTGIS = PG_DATALAGER   # Connection
- DestDataset_POSTGIS_14 = PG_DATALAGER_ADMSRV0118   # Connection

Readers:
- POSTGIS_1: POSTGIS from $(DatabaseSchema)
- XLSXR_1: XLSXR from $(Manifest)

Writers:
- SDF3_1: SDF3 to $(OutputDirectory) in EPSG:3008
- SHAPEFILE_1: SHAPEFILE to $(OutputDirectory) in EPSG:3008
- POSTGIS_2: POSTGIS to $(DestDataset_POSTGIS) in EPSG:3008
- POSTGIS_3: POSTGIS to $(DestDataset_POSTGIS_14) in EPSG:3008

schema (reader XLSXR_1)
    attributes: filter_fme_feature_type char(17), filter_export_column char(10), fme_feature_type_name char(60), column_name char(11), dl_need_new_column_name char(6), dl_new_column_name char(11), dl_export char(6), fme_data_type char(18), native_data_type char(11), fme_format_long_name char(15), fme_format_short_name char(14), _dirpath char(70), _extension char(5), DatasetFull char(15), Dataset char(10), column_name_char_length number(3,0)
    -> Tester
Tester
    BOOL_OP = OR
    TEST_CLAUSE = TEST @Value(dl_export) = true
    TEST_MODE = TEST
    PASSED -> AttributeManager
AttributeManager
    ATTR_TABLE:
      REMOVE filter_fme_feature_type
      REMOVE filter_export_column
      REMOVE column_name
      REMOVE dl_need_new_column_name
      RENAME_SET_VALUE dl_new_column_name > name
      REMOVE dl_export
      REMOVE _dirpath
      REMOVE _extension
      REMOVE DatasetFull
      REMOVE Dataset
      REMOVE column_name_char_length
    -> Aggregator_2
Aggregator_2
    ACCUM_ATTRS_NAME = Use Attributes From One Feature
    AGGREGATE_TYPE = Homogeneous Collection (If Possible)
    COUNT_ATTR = Antal
    GROUP_BY = fme_feature_type fme_feature_type_name fme_format_long_name fme_format_short_name
    LIST_ATTRS_TO_INCLUDE = fme_data_type name native_data_type
    LIST_NAME = attribute
    MODE = Geometry - Assemble One Level
    SEP = ,
    AGGREGATE -> AttributeKeeper_2
AttributeKeeper_2
    CREATE_BULK_MODE_FEATURES = NO
    KEEP_ATTRS = fme_feature_type_name,fme_format_long_name,fme_format_short_name
    KEEP_LIST = attribute{}
    -> FeatureMerger [SUPPLIER]
Note: Workspace som inte används direkt, utan kallas på genom ett s.k. driver-workspace / Parametrar / Parametrarna sätts i DRIVER-skriptet programmatiskt / * [RotDirectory] Kommer från batch-processen och är obligatoriskt för alla FME-processor. / * [ProcessName] Kommer från batch-processen och är obligatoriskt för alla FME-processor. / * [Manifest] Excel-fil från ett tidigare exporterat schema anpassad med nya kolumnnamn samt vilken data som ska exporteras. Används i detta skript för att bygga upp gällande schema för resp. feature type. / * [DatabaseSchema] Informationen hämtas från schema-manifestet. / Databasschemat som tabeller ska exporteras ifrån (motsvarar FME:s dataset). Används även som alias för databasanslutning. Databasanslutningen ska ha samma namn i FME-klienten som kör skriptet. / * [Datatable] Informationen hämtas från schema-manifestet. Tabeller som ska läsas. / * [OutputDirectory] Katalogsökväg för exporterad geodata (delrepository).
ex_markanvandning_l (reader POSTGIS_1)
    attributes: td_id serial,PrimaryKey, sg_localid varchar(250), sg_namespace_id int4,BTree, sg_versionid varchar(250), ma_markanvandningtyp varchar(250),BTree, td_ma_verksamhet_1 varchar(250),BTree, td_ma_verksamhet_2 varchar(250),BTree, ma_namnmarkanvandningobjekt varchar(250), ge_lagesosakerhetplan numeric(5,3), ge_lagesosakerhethojd numeric(5,3), ge_matmetodplan varchar(250),BTree, ge_matmetodhojd varchar(250),BTree, ge_geoidmodell varchar(250),BTree, ge_geometriskupplosning float8, ge_flyghojd int4, ge_skalaunderlag int4, ge_tidpunktmatning timestamp, ge_osakertlage char(1), ge_osakertlageanledning varchar(250), ge_ansvarigorganisation_id int4,BTree, ge_utforandeorganisation_id int4,BTree, ge_hmkstandardniva int4,BTree, ge_foljermatningsanvisning char(1), ge_aktualitet timestamp, td_langd float8, td_notering_text_1 varchar(1000), td_notering_heltal_1 int4, td_notering_decimaltal_1 float8, td_skapad_av varchar(250), td_skapad_datum timestamp,
      td_andrad_av varchar(250), td_andrad_datum timestamp
    -> ParameterFetcher
ParameterFetcher
    ATTR_LIST = ProcessName $(ProcessName) RotDirectory $(RotDirectory)
    -> StringConcatenator
StringConcatenator
    ACTION = Create New Attribute
    PARM_LINE = @Value(ProcessName)_MAIN
    VAL_ATTR = ProcessName_MAIN
    -> UUIDGenerator
UUIDGenerator
    UUID_ATTR = ProcessID
    -> AttributeCreator_3
    -> Sampler_2
AttributeCreator_3
    ATTR_TABLE = SET_TO dl_export = true
    -> SchemaMapper
SchemaMapper
    DATASET = $(Manifest)
    FORMAT = XLSXR
    IDXDESTATTR = fme_feature_type
    IDXDESTCOL = ""
    IDXSOURCEATTR = fme_feature_type
    IDXSOURCECOL = ""
    MAP_ATTRS = column_name dl_new_column_name """"""
    MATCH_ATTRS = filter_export_column dl_export filter_fme_feature_type fme_feature_type_name
    ROW_ID_ATTR = _schemamapper_row_ids
    TABLE = schema
    XLSXR_ALLOW_DOLLAR_SIGNS = YES
    XLSXR_CASE_SENSITIVE_FEATURE_TYPES = YES
    XLSXR_CONFIGURATION_DATASET = C:/dev/Datalager_procsrc/lkr-oracle-topo_karta/_schema/schema-manifest.xlsx
    XLSXR_EXCEL_COL_NAMES = YES
    XLSXR_EXPAND_MERGED_CELLS = Yes
    XLSXR_FORCE_DATETIME = NO
    XLSXR_QUERY_FEATURE_TYPES_FOR_MERGE_FILTERS = Yes
    XLSXR_READ_BLANK_AS = Missing
    XLSXR_SCAN_SCHEMA_IF_DYNAMIC = No
    XLSXR_SCHEMA = schema,0,filter_fme_feature_type,char,17,,,1,filter_export_column,char,10,,,2,fme_feature_type_name,char,15,,,3,column_name,char,21,,,4,dl_need_new_column_name,char,6,,,5,dl_new_column_name,char,11,,,6,dl_export,char,6,,,7,fme_data_type,char,18,,,8,native_data_type,char,15,,,9,fme_format_long_name,char,22,,,10,fme_format_short_name,char,15,,,11,_dirpath,char,1,,,12,_extension,char,1,,,13,DatasetFull,char,11,,,14,Dataset,char,11,,,15,column_name_char_length,number,3,"  0",,1,,,,NO,NO,1,C:/dev/Datalager_procsrc/lkr-oracle-topo_karta/_schema/schema-manifest.xlsx,"0,0,15,841",,NO
    XLSXR_TABLELIST = schema
    XLSXR_USE_SCHEMA_OTHER_FILES = No
    MAPPED -> FeatureMerger [REQUESTOR]
    UNMAPPED -> Aggregator_6
FeatureMerger
    ATTR_ACCUM_MODE = Merge Supplier
    ATTR_CONFLICT_RES = Use Requestor
    IGNORE_NULLS = No
    JOIN_KEYS = @Value(fme_feature_type) @Value(fme_feature_type_name) AUTO
    MERGE_TYPE = Attributes Only
    PROCESS_DUPS = NO
    REJECT_NULL_MISSING_KEYS = No
    SUPPLIERS_FIRST = No
    MERGED -> AttributeExposer
    MERGED -> AttributeExposer_2
    UNMERGED_REQUESTOR -> Aggregator_8
AttributeExposer_2
    ATTR_LIST = md_dettyp,md_plagtyp,td_md_v_1
    -> TestFilter_2
TestFilter_2
    DEFAULT_VALUE = <UNFILTERED>
    PASSED_TEST_GROUP_OUTPUT = FIRST
    TEST_LIST:
      "BOOL_OP,OR,COMPOSITE_TEST,""""""1 OR 2 OR 3 OR 4 OR 5"""""",TEST_CLAUSE,TEST @Value(md_dettyp) = vägbana
      TEST @Value(md_dettyp) = vägbana på tomtmark
      TEST @Value(md_dettyp) = parkering
      TEST @Value(md_dettyp) = gång- och cykelbana
      TEST @Value(md_dettyp) = vägområde",Vägkant,"BOOL_OP,AND,COMPOSITE_TEST,""""""1 AND 2"""""",TEST_CLAUSE,TEST @Value(md_dettyp) = järnväg
      TEST @Value(md_plagtyp) = mitt",järnväg, mitt,"BOOL_OP,AND,COMPOSITE_TEST,""""""1 AND 2"""""",TEST_CLAUSE,TEST @Value(md_dettyp) = järnväg
      TEST @Value(md_plagtyp) = kant",järnväg, kant,"BOOL_OP,COMPOSITE,COMPOSITE_TEST,""""""1 AND 2 AND ( 3 OR 4 )"""""",TEST_CLAUSE,TEST @Value(md_dettyp) = illustration väg
      TEST @Value(md_plagtyp) = mitt
      TEST @Value(td_md_v_1) = gångbana
      TEST @Value(td_md_v_1) = gångstig",gång-bana -stig, mitt,"BOOL_OP,AND,COMPOSITE_TEST,""""""1 AND 2 AND 3"""""",TEST_CLAUSE,TEST @Value(md_dettyp) = illustration väg
      TEST @Value(md_plagtyp) = mitt
      TEST @Value(td_md_v_1) = gc-bana",GC,"BOOL_OP,AND,COMPOSITE_TEST,""""""1 AND 2 AND 3"""""",TEST_CLAUSE,TEST @Value(md_dettyp) = illustration väg
      TEST @Value(md_plagtyp) = mitt
      TEST @Value(td_md_v_1) = planerad",illustration väg, mitt, planerad
    Vägkant -> AttributeCreator_4
    järnväg, mitt -> AttributeCreator_5
    järnväg, kant -> AttributeCreator_6
    gång-bana -stig, mitt -> AttributeCreator_7
    GC -> AttributeCreator_8 [off]
    illustration väg, mitt, planerad -> AttributeCreator_9
Note: GC-mittar borttagna slutet av 2025 i och med överföring till och relation till NVDB
Note: GC-mittar borttagna slutet av 2025 i och med överföring till och relation till NVDB
AttributeExposer
    ATTR_LIST = ml_dettyp,ml_plagtyp,td_ml_v_1
    -> TestFilter
TestFilter
    DEFAULT_VALUE = <UNFILTERED>
    PASSED_TEST_GROUP_OUTPUT = FIRST
    TEST_LIST:
      "BOOL_OP,OR,COMPOSITE_TEST,""""""1 OR 2 OR 3 OR 4 OR 5"""""",TEST_CLAUSE,TEST @Value(ml_dettyp) = vägbana
      TEST @Value(ml_dettyp) = vägbana på tomtmark
      TEST @Value(ml_dettyp) = parkering
      TEST @Value(ml_dettyp) = gång- och cykelbana
      TEST @Value(ml_dettyp) = vägområde",Vägkant,"BOOL_OP,AND,COMPOSITE_TEST,""""""1 AND 2"""""",TEST_CLAUSE,TEST @Value(ml_dettyp) = järnväg
      TEST @Value(ml_plagtyp) = mitt",järnväg, mitt,"BOOL_OP,AND,COMPOSITE_TEST,""""""1 AND 2"""""",TEST_CLAUSE,TEST @Value(ml_dettyp) = järnväg
      TEST @Value(ml_plagtyp) = kant",järnväg, kant,"BOOL_OP,COMPOSITE,COMPOSITE_TEST,""""""1 AND 2 AND ( 3 OR 4 )"""""",TEST_CLAUSE,TEST @Value(ml_dettyp) = illustration väg
      TEST @Value(ml_plagtyp) = mitt
      TEST @Value(td_ml_v_1) = gångbana
      TEST @Value(td_ml_v_1) = gångstig",gång-bana -stig, mitt,"BOOL_OP,AND,COMPOSITE_TEST,""""""1 AND 2 AND 3"""""",TEST_CLAUSE,TEST @Value(ml_dettyp) = illustration väg
      TEST @Value(ml_plagtyp) = mitt
      TEST @Value(td_ml_v_1) = gc-bana",GC,"BOOL_OP,AND,COMPOSITE_TEST,""""""1 AND 2 AND 3"""""",TEST_CLAUSE,TEST @Value(ml_dettyp) = illustration väg
      TEST @Value(ml_plagtyp) = mitt
      TEST @Value(td_ml_v_1) = planerad",illustration väg, mitt, planerad
    Vägkant -> AttributeCreator_4
    järnväg, mitt -> AttributeCreator_5
    järnväg, kant -> AttributeCreator_6
    gång-bana -stig, mitt -> AttributeCreator_7
    GC -> AttributeCreator_8 [off]
    illustration väg, mitt, planerad -> AttributeCreator_9
Note: AttributeCreator_4 [AttributeCreator Version 9] / Attributes To Create: New AttributeAttribute Value_name_extension_vag_kant
AttributeCreator_4
    ATTR_TABLE = SET_TO _name_extension = _vag_kant
    -> Junction_2
Note: AttributeCreator_5 [AttributeCreator Version 9] / Attributes To Create: New AttributeAttribute Value_name_extension_jarnvag_mitt
AttributeCreator_5
    ATTR_TABLE = SET_TO _name_extension = _jarnvag_mitt
    -> Junction_2
Note: AttributeCreator_6 [AttributeCreator Version 9] / Attributes To Create: New AttributeAttribute Value_name_extension_jarnvag_kant
AttributeCreator_6
    ATTR_TABLE = SET_TO _name_extension = _jarnvag_kant
    -> Junction_2
Note: AttributeCreator_7 [AttributeCreator Version 9] / Attributes To Create: New AttributeAttribute Value_name_extension_gangbana_mitt
AttributeCreator_7
    ATTR_TABLE = SET_TO _name_extension = _gangbana_mitt
    -> Junction_2
Note: AttributeCreator_8 [AttributeCreator Version 9] / Attributes To Create: New AttributeAttribute Value_name_extension_gc_mitt
AttributeCreator_8
    ATTR_TABLE = SET_TO _name_extension = _gc_mitt
    -> Junction_2
Note: AttributeCreator_9 [AttributeCreator Version 9] / Attributes To Create: New AttributeAttribute Value_name_extension_illustration_vag_mitt_planerad
AttributeCreator_9
    ATTR_TABLE = SET_TO _name_extension = _illustration_vag_mitt_planerad
    -> Junction_2
Junction_2
    -> CoordinateSystemRemover
CoordinateSystemRemover
    -> AttributeCopier
AttributeCopier
    ATTR_TABLE = COPY fme_feature_type > _name
    -> StringReplacer
StringReplacer
    CASE = NO
    FIND_TEXT = (_p|_l|_y|_t)$
    NO_MATCH = _FME_NO_OP_
    REGEXP = YES
    SRC_ATTRS = _name
    -> StringReplacer_2
StringReplacer_2
    CASE = NO
    FIND_TEXT = ^td_baskarta.
    NO_MATCH = _FME_NO_OP_
    REGEXP = YES
    SRC_ATTRS = _name
    -> ArcStroker
Note: ArcStroker [ArcStroker Version 5] / General: / Stroke By: Maximum Deviation / Maximum Deviation: 0.02 / Make Polygon Out of 360 Degree Arcs: No
ArcStroker
    MAKE_POLY = No
    STROKE_CHOICE = Maximum Deviation
    TOLERANCE_VAL = 0.02
    STROKED -> 2DForcer
2DForcer
    2D -> GeometryRefiner
GeometryRefiner
    -> GeometryFilter
GeometryFilter
    BREAK_AGG = No
    GEOM_PORT_NAMES = Point Line Arc Area Ellipse Text Raster "Point Cloud" Surface Solid Collection Null Instance
    POINT -> StringConcatenator_4
    LINE -> StringConcatenator_5
    ARC -> StringConcatenator_31
    AREA -> StringConcatenator_6
    ELLIPSE -> StringConcatenator_32
    TEXT -> StringConcatenator_7
    RASTER -> Junction_6
    POINTCLOUD -> Junction_6
    SURFACE -> Junction_6
    SOLID -> Junction_6
    COLLECTION -> Junction_6
    NULL -> Junction_6
    INSTANCE -> Junction_6
    <UNFILTERED> -> Junction_6
StringConcatenator_4
    ACTION = Create New Attribute
    PARM_LINE = @Value(_name)@Value(_name_extension)_p
    VAL_ATTR = DatasetName
    -> StringCaseChanger_5
    -> Junction
StringConcatenator_5
    ACTION = Create New Attribute
    PARM_LINE = @Value(_name)@Value(_name_extension)_l
    VAL_ATTR = DatasetName
    -> StringCaseChanger_2
    -> Junction
StringConcatenator_31
    ACTION = Create New Attribute
    PARM_LINE = @Value(_name)@Value(_name_extension)_l
    VAL_ATTR = DatasetName
    -> StringCaseChanger_3
    -> Junction
StringConcatenator_6
    ACTION = Create New Attribute
    PARM_LINE = @Value(_name)@Value(_name_extension)_y
    VAL_ATTR = DatasetName
    -> StringCaseChanger_4
    -> Junction
StringConcatenator_32
    ACTION = Create New Attribute
    PARM_LINE = @Value(_name)@Value(_name_extension)_y
    VAL_ATTR = DatasetName
    -> StringCaseChanger_6
    -> Junction
StringConcatenator_7
    ACTION = Create New Attribute
    PARM_LINE = @Value(_name)@Value(_name_extension)_t
    VAL_ATTR = DatasetName
    -> StringCaseChanger_5
    -> Junction
Junction
    -> NullAttributeMapper
    -> schema (writer POSTGIS_2)
    -> Table1 (writer POSTGIS_3)
    -> Aggregator_4
NullAttributeMapper
    ATTRCHOICE = All Attributes
    NULL_TREATMENT = Null
    SOURCE_ATTR_VAL = Null
    -> StringCaseChanger
Note: Aggregator : Input
Junction_6
    -> Junction_7
Creator
    GEOMTYPE = Geometry Object
    NUM = 1
    CREATED -> ParameterFetcher_2
ParameterFetcher_2
    ATTR_LIST = ProcessName $(ProcessName) RotDirectory $(RotDirectory)
    -> StringConcatenator_8
StringConcatenator_8
    ACTION = Create New Attribute
    PARM_LINE = @Value(ProcessName)_MAIN
    VAL_ATTR = ProcessName_MAIN
    -> UUIDGenerator_2
UUIDGenerator_2
    UUID_ATTR = ProcessID
    -> AttributeCreator_12
AttributeCreator_12
    ATTR_TABLE = SET_TO _FeatureIdMerger = 1
    -> AttributeCreator_12_OUTPUT
AttributeCreator_12_OUTPUT: Junction
    -> FeatureMerger_2 [SUPPLIER]
    -> FeatureMerger_3 [SUPPLIER]
    -> FeatureMerger_4 [SUPPLIER]
    -> FeatureMerger_6 [SUPPLIER]
    -> FeatureMerger_7 [SUPPLIER]

Bookmark: FDO_Line
StringCaseChanger_2
    ATTRCHOICE = Selected Attributes
    ATTRLIST = DatasetName
    CHANGE_TYPE = lowercase
    -> FeatureClass10000 (writer SDF3_1)
Note: : lkr_gis [SDF3] Line
FeatureClass10000 (writer SDF3_1)

Bookmark: FDO_Arc
StringCaseChanger_3
    ATTRCHOICE = Selected Attributes
    ATTRLIST = DatasetName
    CHANGE_TYPE = lowercase
    -> FeatureClass10001 (writer SDF3_1)
Note: : lkr_gis [SDF3] Arc
FeatureClass10001 (writer SDF3_1)

Bookmark: FDO_Area
StringCaseChanger_4
    ATTRCHOICE = Selected Attributes
    ATTRLIST = DatasetName
    CHANGE_TYPE = lowercase
    -> FeatureClass10002 (writer SDF3_1)
Note: : lkr_gis [SDF3] Area
FeatureClass10002 (writer SDF3_1)

Bookmark: FDO_Ellipse
StringCaseChanger_6
    ATTRCHOICE = Selected Attributes
    ATTRLIST = DatasetName
    CHANGE_TYPE = lowercase
    -> FeatureClass10003 (writer SDF3_1)
Note: : lkr_gis [SDF3] Ellipse
FeatureClass10003 (writer SDF3_1)

Bookmark: FDO_Point
StringCaseChanger_5
    ATTRCHOICE = Selected Attributes
    ATTRLIST = DatasetName
    CHANGE_TYPE = lowercase
    -> FeatureClass100 (writer SDF3_1)
Note: : lkr_gis [SDF3] Point
FeatureClass100 (writer SDF3_1)

Bookmark: SHAPE
StringCaseChanger
    ATTRCHOICE = Selected Attributes
    ATTRLIST = DatasetName
    CHANGE_TYPE = lowercase
    -> Shapefile1 (writer SHAPEFILE_1)
Note: : [SHAPEFILE]
Shapefile1 (writer SHAPEFILE_1)

Bookmark: PostGIS
Note: BUGG (FME 2021.0): / "Table Qualifier" i writer fungerar inte med dynamisk skrivning. Värdet behöver konkatineras i "Table Name"
schema (writer POSTGIS_2)
Table1 (writer POSTGIS_3)

Bookmark: Loggning
Aggregator_4
    ACCUM_ATTRS_NAME = Use Attributes From One Feature
    AGGREGATE_TYPE = Homogeneous Collection (If Possible)
    COUNT_ATTR = Antal
    MODE = Geometry - Assemble One Level
    SEP = ", "
    AGGREGATE -> FeatureMerger_4 [REQUESTOR]
Note: GeometryFilter_RASTER : Output
Junction_7
    -> Aggregator
Aggregator
    ACCUM_ATTRS_NAME = Use Attributes From One Feature
    AGGREGATE_TYPE = Homogeneous Collection (If Possible)
    GROUP_BY = fme_feature_type
    MODE = Geometry - Assemble One Level
    ORDERED = No
    SEP = ,
    AGGREGATE -> Aggregator_3
Aggregator_3
    ACCUM_ATTRS_NAME = Use Attributes From One Feature
    AGGREGATE_TYPE = Homogeneous Collection (If Possible)
    CONCAT_ATTRS = fme_feature_type
    COUNT_ATTR = Antal
    MODE = Geometry - Assemble One Level
    ORDERED = No
    SEP = ", "
    AGGREGATE -> AttributeCreator_2
AttributeCreator_2
    ATTR_TABLE = SET_TO _FeatureIdMerger = 1
    -> FeatureMerger_3 [REQUESTOR]
Aggregator_8
    ACCUM_ATTRS_NAME = Use Attributes From One Feature
    AGGREGATE_TYPE = Homogeneous Collection (If Possible)
    GROUP_BY = fme_feature_type
    MODE = Geometry - Assemble One Level
    SEP = ", "
    AGGREGATE -> Aggregator_9
Aggregator_9
    ACCUM_ATTRS_NAME = Use Attributes From One Feature
    AGGREGATE_TYPE = Homogeneous Collection (If Possible)
    CONCAT_ATTRS = fme_feature_type
    MODE = Geometry - Assemble One Level
    SEP = ", "
    AGGREGATE -> FeatureMerger_7 [REQUESTOR]
Aggregator_6
    ACCUM_ATTRS_NAME = Use Attributes From One Feature
    AGGREGATE_TYPE = Homogeneous Collection (If Possible)
    GROUP_BY = fme_feature_type
    MODE = Geometry - Assemble One Level
    SEP = ", "
    AGGREGATE -> Aggregator_7
Aggregator_7
    ACCUM_ATTRS_NAME = Use Attributes From One Feature
    AGGREGATE_TYPE = Homogeneous Collection (If Possible)
    CONCAT_ATTRS = fme_feature_type
    MODE = Geometry - Assemble One Level
    SEP = ", "
    AGGREGATE -> FeatureMerger_6 [REQUESTOR]
Note: Endast till för som signal att starta logg
Sampler_2
    RATE = 1
    SAMPLE_MODE = No
    SAMPLE_TYPE_LONG = First N Features
    SAMPLED -> AttributeCreator_13
AttributeCreator_13
    ATTR_TABLE = SET_TO _FeatureIdMerger = 1
    -> FeatureMerger_2 [REQUESTOR]
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_9
StringConcatenator_9
    ACTION = Create New Attribute
    PARM_LINE = @Value(ProcessName_MAIN) avslutad med @Value(Antal) st. objekt skrivna till datalagret.
    VAL_ATTR = Logg
    -> DTStamperYYYY-MM-DD_HH:MI:SS.sss_4
DTStamperYYYY-MM-DD_HH:MI:SS.sss_4
    -> Logg_4
Logg_4: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,KLART,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_7
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_12
StringConcatenator_12
    ACTION = Create New Attribute
    PARM_LINE = fme_basicstring:12%24%180:Dataset(en) @Value(fme_feature_type) har ej länkats till något schema. Kommer ej att kunna skapas med attribut. Kontrollera anledningen till att dataset åkt igenom utan upptagning på korrekt sätt i schemahanteringen.
    VAL_ATTR = Logg
    -> DTStamperYYYY-MM-DD_HH:MI:SS.sss_6
DTStamperYYYY-MM-DD_HH:MI:SS.sss_6
    -> Logg_7
Logg_7: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_2
    ATTR_ACCUM_MODE = Merge Supplier
    ATTR_CONFLICT_RES = Use Requestor
    IGNORE_NULLS = No
    JOIN_KEYS = @Value(_FeatureIdMerger) @Value(_FeatureIdMerger) AUTO
    MERGE_TYPE = Attributes Only
    PROCESS_DUPS = No
    REJECT_NULL_MISSING_KEYS = No
    SUPPLIERS_FIRST = No
    MERGED -> StringConcatenator_2
StringConcatenator_2
    ACTION = Create New Attribute
    PARM_LINE = Kör @Value(ProcessName_MAIN) för data "$(DatabaseSchema).$(Datatable)" till datalagret.
    VAL_ATTR = Logg
    -> DTStamperYYYY-MM-DD_HH:MI:SS.sss
DTStamperYYYY-MM-DD_HH:MI:SS.sss
    -> Logg_2
Logg_2: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,INFORMATION,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_6
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_11
StringConcatenator_11
    ACTION = Create New Attribute
    PARM_LINE = fme_basicstring:37%24%31:Kolumner och dess namn i dataset(en) @Value(fme_feature_type) har ej länkats till nytt namn.
    VAL_ATTR = Logg
    -> DTStamperYYYY-MM-DD_HH:MI:SS.sss_5
DTStamperYYYY-MM-DD_HH:MI:SS.sss_5
    -> Logg_6
Logg_6: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_3
    ATTR_ACCUM_MODE = Merge Supplier
    ATTR_CONFLICT_RES = Use Requestor
    IGNORE_NULLS = No
    JOIN_KEYS = @Value(_FeatureIdMerger) @Value(_FeatureIdMerger) AUTO
    MERGE_TYPE = Attributes Only
    PROCESS_DUPS = No
    REJECT_NULL_MISSING_KEYS = No
    SUPPLIERS_FIRST = No
    MERGED -> StringConcatenator_3
StringConcatenator_3
    ACTION = Create New Attribute
    PARM_LINE = Geometrier från objektklasser (@Value(fme_feature_type)) skrivs ej till shape-filer.
    VAL_ATTR = Logg
    -> DTStamperYYYY-MM-DD_HH:MI:SS.sss_2
DTStamperYYYY-MM-DD_HH:MI:SS.sss_2
    -> Logg_3
Logg_3: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,VARNING,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    INCLUDE_OFFSET = NO
    STAMP_TYPE = datetime
    TIMEZONE = local
    -> DateTimeConverter
DateTimeConverter
    DATETIME_ATTR = _dts
    OUT_FORMAT = %Y-%m-%d %H:%M:%S
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    NO_MATCH = _FME_NO_OP_
    REGEXP = YES
    SRC_ATTRS = _dts
    -> StringReplacer_2
StringReplacer_2
    CASE = NO
    FIND_TEXT = .*\.
    NO_MATCH = _FME_NO_OP_
    REGEXP = YES
    SRC_ATTRS = _mils
    -> SubstringExtractor
SubstringExtractor
    END = 2
    RESULT_ATTR = _subMils
    SRC_STRING = @Value(_mils)
    START = 0
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)
