FME workspace postgis-td_drk_anpassat-DatalagerManage.fmw

Parameters:
- DestDataset_POSTGIS =
- DestDataset_POSTGIS_27 =
- DestDataset_POSTGIS_28 =
- DestDataset_POSTGIS_29 =
- DestDataset_POSTGIS_30 =
- DestDataset_POSTGIS_ADMSRV0118 =
- Drift =
- FME_USER_PARAM_PRIVATE_GRP =
- IsWholeProcessRun =
- Manifest =
- OutSchemaFileNameSuffix =
- OutputDirectory =
- PARAMETER_4 =
- PG_SCHEMA =
- ProcessModulName =
- ProcessName =
- RotDirectory =
- SchemaFlush =

Readers:
- XLSXR_1: XLSXR from $(SchemaFlush)
- SCHEMA_FROM_TABLE_1: SCHEMA_FROM_TABLE from $(Manifest)

Writers:
- ESRISHAPE_1: ESRISHAPE to $(OutputDirectory)
- SDF3_1: SDF3 to $(OutputDirectory) in EPSG:3008
- SHAPEFILE_1: SHAPEFILE to $(OutputDirectory) in EPSG:3008
- POSTGIS_1: POSTGIS to $(DestDataset_POSTGIS) in EPSG:3008
- POSTGIS_2: POSTGIS to $(DestDataset_POSTGIS) in EPSG:3008
- POSTGIS_3: POSTGIS to $(DestDataset_POSTGIS) in EPSG:3008
- POSTGIS_4: POSTGIS to $(DestDataset_POSTGIS) in EPSG:3008
- POSTGIS_5: POSTGIS to $(DestDataset_POSTGIS) in EPSG:3008
- POSTGIS_6: POSTGIS to $(DestDataset_POSTGIS) in EPSG:3008
- POSTGIS_7: POSTGIS to $(DestDataset_POSTGIS) in EPSG:3008
- POSTGIS_8: POSTGIS to $(DestDataset_POSTGIS) in EPSG:3008
- POSTGIS_9: POSTGIS to $(DestDataset_POSTGIS) in EPSG:3008
- POSTGIS_10: POSTGIS to $(DestDataset_POSTGIS) in EPSG:3008
- POSTGIS_11: POSTGIS to $(DestDataset_POSTGIS) in EPSG:3008
- POSTGIS_12: POSTGIS to $(DestDataset_POSTGIS_30) in EPSG:3008
- POSTGIS_13: POSTGIS to $(DestDataset_POSTGIS_29) in EPSG:3008
- POSTGIS_14: POSTGIS to $(DestDataset_POSTGIS_ADMSRV0118) in EPSG:3008
- POSTGIS_15: POSTGIS to $(DestDataset_POSTGIS_ADMSRV0118) in EPSG:3008
- POSTGIS_16: POSTGIS to $(DestDataset_POSTGIS_ADMSRV0118) in EPSG:3008
- POSTGIS_17: POSTGIS to $(DestDataset_POSTGIS_ADMSRV0118) in EPSG:3008
- POSTGIS_18: POSTGIS to $(DestDataset_POSTGIS_ADMSRV0118) in EPSG:3008
- POSTGIS_19: POSTGIS to $(DestDataset_POSTGIS_ADMSRV0118) in EPSG:3008
- POSTGIS_20: POSTGIS to $(DestDataset_POSTGIS_ADMSRV0118) in EPSG:3008
- POSTGIS_21: POSTGIS to $(DestDataset_POSTGIS_ADMSRV0118) in EPSG:3008
- POSTGIS_22: POSTGIS to $(DestDataset_POSTGIS_ADMSRV0118) in EPSG:3008
- POSTGIS_23: POSTGIS to $(DestDataset_POSTGIS_ADMSRV0118) in EPSG:3008
- POSTGIS_24: POSTGIS to $(DestDataset_POSTGIS_ADMSRV0118) in EPSG:3008
- POSTGIS_25: POSTGIS to $(DestDataset_POSTGIS_28) in EPSG:3008
- POSTGIS_26: POSTGIS to $(DestDataset_POSTGIS_27) in EPSG:3008

Creator
    GEOMTYPE = Geometry Object
    NUM = 1
    CREATED -> ParameterFetcher_2
ParameterFetcher_2
    ATTR_LIST = ProcessName $(ProcessName) RotDirectory $(RotDirectory)
    -> UUIDGenerator_2
UUIDGenerator_2
    UUID_ATTR = ProcessID
    -> AttributeCreator_12_OUTPUT_-__FeatureMerger_3_SUPPLIER
AttributeCreator_12_OUTPUT_-__FeatureMerger_3_SUPPLIER: Junction
    -> Junction
    -> Junction_3
    -> Junction_7
    -> Junction_9
    -> Junction_13
    -> Junction_14
    -> Junction_16
    -> Junction_18
    -> Junction_20
Note: FeatureMerger_2 : Supplier
Junction
    -> Junction_2
Note: FeatureMerger_3 : Supplier
Junction_3
    -> Junction_4
Note: FeatureMerger_5 : Supplier
Junction_7
Note: FeatureMerger_6 : Supplier
Junction_9
    -> Junction_10
Note: Junction_8 : Input
Junction_16
    -> Junction_8
Note: Junction_6 : Input
Junction_14
    -> Junction_15
Note: Junction_12 : Input
Junction_13
Note: Junction_17 : Input
Junction_18
    -> Junction_17
Note: Junction_19 : Input
Junction_20
    -> Junction_19
Note: Parametrar / * [RotDirectory] Kommer från batch-processen och är obligatoriskt för alla FME-processor. / * [ProcessName] Kommer från batch-processen och är obligatoriskt för alla FME-processor. / * [Manifest] Excel-fil från ett tidigare exporterat schema anpassad med nya kolumnnamn samt vilken data som ska exporteras. / * [OutputDirectory] Katalogsökväg för exporterad geodata (delrepository).
schema (reader XLSXR_1)
    attributes: fme_feature_type_name char(20), column_name char(16), dl_need_new_column_name char(6), dl_new_column_name char(12), dl_export char(5), fme_data_type char(18), native_data_type char(14), fme_format_long_name char(22), fme_format_short_name char(15), _dirpath char(1), _extension char(1), DatasetFull char(8), Dataset char(8), column_name_char_length number(3,0)
    -> Tester_4
Tester_4
    BOOL_OP = OR
    TEST_CLAUSE = TEST @Value(dl_export) = true
    TEST_MODE = TEST
    PASSED -> Tester_2
    PASSED -> Aggregator_3
    PASSED -> Sampler_2
Aggregator_3
    ACCUM_ATTRS_NAME = Drop Incoming Attributes
    AGGREGATE_TYPE = Homogeneous Collection (If Possible)
    GROUP_BY = fme_feature_type_name fme_format_short_name Dataset
    MODE = Geometry - Assemble One Level
    ORDERED = No
    SEP = ,
    AGGREGATE -> StringConcatenator
StringConcatenator
    ACTION = Create New Attribute
    PARM_LINE = @Value(fme_feature_type_name)
    VAL_ATTR = _filterValue
    -> StringCaseChanger
StringCaseChanger
    ATTRCHOICE = Selected Attributes
    ATTRLIST = _filterValue
    CHANGE_TYPE = lowercase
    -> TestFilter_2
TestFilter_2
    DEFAULT_VALUE = <UNFILTERED>
    TEST_LIST = "BOOL_OP,OR,COMPOSITE_TEST,""""""<Unused>"""""",TEST_CLAUSE,TEST @Value(_filterValue) = td_drk.rk_3dfastighet_y",td_drk.rk_3dfastighet_y,"BOOL_OP,OR,COMPOSITE_TEST,""""""<Unused>"""""",TEST_CLAUSE,TEST @Value(_filterValue) = td_drk.rk_3dfastighet_y_ism_ap",td_drk.rk_3dfastighet_y_ism_ap,"BOOL_OP,OR,COMPOSITE_TEST,""""""<Unused>"""""",TEST_CLAUSE,TEST @Value(_filterValue) = td_drk.rk_3dfastighetid_p",td_drk.rk_3dfastighetid_p,"BOOL_OP,OR,COMPOSITE_TEST,""""""<Unused>"""""",TEST_CLAUSE,TEST @Value(_filterValue) = td_drk.rk_3dfastighetid_p_ism_ap",td_drk.rk_3dfastighetid_p_ism_ap,"BOOL_OP,OR,COMPOSITE_TEST,""""""<Unused>"""""",TEST_CLAUSE,TEST @Value(_filterValue) = td_drk.rk_3dfastighetidtext_p",td_drk.rk_3dfastighetidtext_p,"BOOL_OP,OR,COMPOSITE_TEST,""""""<Unused>"""""",TEST_CLAUSE,TEST @Value(_filterValue) = td_drk.rk_3dfastighetidtext_p_ism_ap",td_drk.rk_3dfastighetidtext_p_ism_ap,"BOOL_OP,OR,COMPOSITE_TEST,""""""<Unused>"""""",TEST_CLAUSE,TEST @Value(_filterValue) = td_drk.rk_3dfastighetomrade_l",td_drk.rk_3dfastighetomrade_l,"BOOL_OP,OR,COMPOSITE_TEST,""""""<Unused>"""""",TEST_CLAUSE,TEST @Value(_filterValue) = td_drk.rk_3dfastighetomrade_l_ism_ap",td_drk.rk_3dfastighetomrade_l_ism_ap,"BOOL_OP,OR,COMPOSITE_TEST,""""""<Unused>"""""",TEST_CLAUSE,TEST @Value(_filterValue) = td_drk.rk_bestammelse_l",td_drk.rk_bestammelse_l,"BOOL_OP,OR,COMPOSITE_TEST,""""""<Unused>"""""",TEST_CLAUSE,TEST @Value(_filterValue) = td_drk.rk_bestammelse_l_ism_ap",td_drk.rk_bestammelse_l_ism_ap,"BOOL_OP,OR,COMPOSITE_TEST,""""""<Unused>"""""",TEST_CLAUSE,TEST @Value(_filterValue) = td_drk.rk_bestammelse_y",td_drk.rk_bestammelse_y,"BOOL_OP,OR,COMPOSITE_TEST,""""""<Unused>"""""",TEST_CLAUSE,TEST @Value(_filterValue) = td_drk.rk_bestammelse_y_ism_ap",td_drk.rk_bestammelse_y_ism_ap,"BOOL_OP,OR,COMPOSITE_TEST,""""""<Unused>"""""",TEST_CLAUSE,TEST @Value(_filterValue) = td_drk.rk_bestammelseadmtext_p",td_drk.rk_bestammelseadmtext_p,"BOOL_OP,OR,COMPOSITE_TEST,""""""<Unused>"""""",TEST_CLAUSE,TEST @Value(_filterValue) = td_drk.rk_bestammelseadmtext_p_ism_ap",td_drk.rk_bestammelseadmtext_p_ism_ap,"BOOL_OP,OR,COMPOSITE_TEST,""""""<Unused>"""""",TEST_CLAUSE,TEST @Value(_filterValue) = td_drk.rk_bestammelseid_p",td_drk.rk_bestammelseid_p,"BOOL_OP,OR,COMPOSITE_TEST,""""""<Unused>"""""",TEST_CLAUSE,TEST @Value(_filterValue) = td_drk.rk_bestammelseid_p_ism_ap",td_drk.rk_bestammelseid_p_ism_ap,"BOOL_OP,OR,COMPOSITE_TEST,""""""<Unused>"""""",TEST_CLAUSE,TEST @Value(_filterValue) = td_drk.rk_bestammelseomrade_l",td_drk.rk_bestammelseomrade_l,"BOOL_OP,OR,COMPOSITE_TEST,""""""<Unused>"""""",TEST_CLAUSE,TEST @Value(_filterValue) = td_drk.rk_bestammelseomrade_l_ism_ap",td_drk.rk_bestammelseomrade_l_ism_ap,"BOOL_OP,OR,COMPOSITE_TEST,""""""<Unused>"""""",TEST_CLAUSE,TEST @Value(_filterValue) = td_drk.rk_bestammelsetext_p",td_drk.rk_bestammelsetext_p,"BOOL_OP,OR,COMPOSITE_TEST,""""""<Unused>"""""",TEST_CLAUSE,TEST @Value(_filterValue) = td_drk.rk_bestammelsetext_p_ism_ap",td_drk.rk_bestammelsetext_p_ism_ap,"BOOL_OP,OR,COMPOSITE_TEST,""""""<Unused>"""""",TEST_CLAUSE,TEST @Value(_filterValue) = td_drk.rk_fastighet_l",td_drk.rk_fastighet_l,"BOOL_OP,OR,COMPOSITE_TEST,""""""<Unused>"""""",TEST_CLAUSE,TEST @Value(_filterValue) = td_drk.rk_fastighet_l_ism_ap",td_drk.rk_fastighet_l_ism_ap,"BOOL_OP,OR,COMPOSITE_TEST,""""""<Unused>"""""",TEST_CLAUSE,TEST @Value(_filterValue) = td_drk.rk_fastighet_p",td_drk.rk_fastighet_p,"BOOL_OP,OR,COMPOSITE_TEST,""""""<Unused>"""""",TEST_CLAUSE,TEST @Value(_filterValue) = td_drk.rk_fastighet_p_ism_ap",td_drk.rk_fastighet_p_ism_ap,"BOOL_OP,OR,COMPOSITE_TEST,""""""<Unused>"""""",TEST_CLAUSE,TEST @Value(_filterValue) = td_drk.rk_fastighet_y",td_drk.rk_fastighet_y,"BOOL_OP,OR,COMPOSITE_TEST,""""""<Unused>"""""",TEST_CLAUSE,TEST @Value(_filterValue) = td_drk.rk_fastighet_y_ism_ap",td_drk.rk_fastighet_y_ism_ap,"BOOL_OP,OR,COMPOSITE_TEST,""""""<Unused>"""""",TEST_CLAUSE,TEST @Value(_filterValue) = td_drk.rk_fastighetadmtext_p",td_drk.rk_fastighetadmtext_p,"BOOL_OP,OR,COMPOSITE_TEST,""""""<Unused>"""""",TEST_CLAUSE,TEST @Value(_filterValue) = td_drk.rk_fastighetadmtext_p_ism_ap",td_drk.rk_fastighetadmtext_p_ism_ap,"BOOL_OP,OR,COMPOSITE_TEST,""""""<Unused>"""""",TEST_CLAUSE,TEST @Value(_filterValue) = td_drk.rk_fastighetgrans_l",td_drk.rk_fastighetgrans_l,"BOOL_OP,OR,COMPOSITE_TEST,""""""<Unused>"""""",TEST_CLAUSE,TEST @Value(_filterValue) = td_drk.rk_fastighetgrans_l_ism_ap",td_drk.rk_fastighetgrans_l_ism_ap,"BOOL_OP,OR,COMPOSITE_TEST,""""""<Unused>"""""",TEST_CLAUSE,TEST @Value(_filterValue) = td_drk.rk_fastighetid_p",td_drk.rk_fastighetid_p,"BOOL_OP,OR,COMPOSITE_TEST,""""""<Unused>"""""",TEST_CLAUSE,TEST @Value(_filterValue) = td_drk.rk_fastighetid_p_ism_ap",td_drk.rk_fastighetid_p_ism_ap,"BOOL_OP,OR,COMPOSITE_TEST,""""""<Unused>"""""",TEST_CLAUSE,TEST @Value(_filterValue) = td_drk.rk_fastighetidtext_p",td_drk.rk_fastighetidtext_p,"BOOL_OP,OR,COMPOSITE_TEST,""""""<Unused>"""""",TEST_CLAUSE,TEST @Value(_filterValue) = td_drk.rk_fastighetidtext_p_ism_ap",td_drk.rk_fastighetidtext_p_ism_ap,"BOOL_OP,OR,COMPOSITE_TEST,""""""<Unused>"""""",TEST_CLAUSE,TEST @Value(_filterValue) = td_drk.rk_fastighettext_p",td_drk.rk_fastighettext_p,"BOOL_OP,OR,COMPOSITE_TEST,""""""<Unused>"""""",TEST_CLAUSE,TEST @Value(_filterValue) = td_drk.rk_fastighettext_p_ism_ap",td_drk.rk_fastighettext_p_ism_ap,"BOOL_OP,OR,COMPOSITE_TEST,""""""<Unused>"""""",TEST_CLAUSE,TEST @Value(_filterValue) = td_drk.rk_ga_l",td_drk.rk_ga_l,"BOOL_OP,OR,COMPOSITE_TEST,""""""<Unused>"""""",TEST_CLAUSE,TEST @Value(_filterValue) = td_drk.rk_ga_l_ism_ap",td_drk.rk_ga_l_ism_ap,"BOOL_OP,OR,COMPOSITE_TEST,""""""<Unused>"""""",TEST_CLAUSE,TEST @Value(_filterValue) = td_drk.rk_ga_p",td_drk.rk_ga_p,"BOOL_OP,OR,COMPOSITE_TEST,""""""<Unused>"""""",TEST_CLAUSE,TEST @Value(_filterValue) = td_drk.rk_ga_p_ism_ap",td_drk.rk_ga_p_ism_ap,"BOOL_OP,OR,COMPOSITE_TEST,""""""<Unused>"""""",TEST_CLAUSE,TEST @Value(_filterValue) = td_drk.rk_ga_y",td_drk.rk_ga_y,"BOOL_OP,OR,COMPOSITE_TEST,""""""<Unused>"""""",TEST_CLAUSE,TEST @Value(_filterValue) = td_drk.rk_ga_y_ism_ap",td_drk.rk_ga_y_ism_ap,"BOOL_OP,OR,COMPOSITE_TEST,""""""<Unused>"""""",TEST_CLAUSE,TEST @Value(_filterValue) = td_drk.rk_gaomrade_l",td_drk.rk_gaomrade_l,"BOOL_OP,OR,COMPOSITE_TEST,""""""<Unused>"""""",TEST_CLAUSE,TEST @Value(_filterValue) = td_drk.rk_gaomrade_l_ism_ap",td_drk.rk_gaomrade_l_ism_ap,"BOOL_OP,OR,COMPOSITE_TEST,""""""<Unused>"""""",TEST_CLAUSE,TEST @Value(_filterValue) = td_drk.rk_gatext_p",td_drk.rk_gatext_p,"BOOL_OP,OR,COMPOSITE_TEST,""""""<Unused>"""""",TEST_CLAUSE,TEST @Value(_filterValue) = td_drk.rk_gatext_p_ism_ap",td_drk.rk_gatext_p_ism_ap,"BOOL_OP,OR,COMPOSITE_TEST,""""""<Unused>"""""",TEST_CLAUSE,TEST @Value(_filterValue) = td_drk.rk_granspunkt_p",td_drk.rk_granspunkt_p,"BOOL_OP,OR,COMPOSITE_TEST,""""""<Unused>"""""",TEST_CLAUSE,TEST @Value(_filterValue) = td_drk.rk_granspunkt_p_ism_ap",td_drk.rk_granspunkt_p_ism_ap,"BOOL_OP,OR,COMPOSITE_TEST,""""""<Unused>"""""",TEST_CLAUSE,TEST @Value(_filterValue) = td_drk.rk_plan_y",td_drk.rk_plan_y,"BOOL_OP,OR,COMPOSITE_TEST,""""""<Unused>"""""",TEST_CLAUSE,TEST @Value(_filterValue) = td_drk.rk_plan_y_ism_ap",td_drk.rk_plan_y_ism_ap,"BOOL_OP,OR,COMPOSITE_TEST,""""""<Unused>"""""",TEST_CLAUSE,TEST @Value(_filterValue) = td_drk.rk_planadmtext_p",td_drk.rk_planadmtext_p,"BOOL_OP,OR,COMPOSITE_TEST,""""""<Unused>"""""",TEST_CLAUSE,TEST @Value(_filterValue) = td_drk.rk_planadmtext_p_ism_ap",td_drk.rk_planadmtext_p_ism_ap,"BOOL_OP,OR,COMPOSITE_TEST,""""""<Unused>"""""",TEST_CLAUSE,TEST @Value(_filterValue) = td_drk.rk_planid_p",td_drk.rk_planid_p,"BOOL_OP,OR,COMPOSITE_TEST,""""""<Unused>"""""",TEST_CLAUSE,TEST @Value(_filterValue) = td_drk.rk_planid_p_ism_ap",td_drk.rk_planid_p_ism_ap,"BOOL_OP,OR,COMPOSITE_TEST,""""""<Unused>"""""",TEST_CLAUSE,TEST @Value(_filterValue) = td_drk.rk_planidtext_p",td_drk.rk_planidtext_p,"BOOL_OP,OR,COMPOSITE_TEST,""""""<Unused>"""""",TEST_CLAUSE,TEST @Value(_filterValue) = td_drk.rk_planidtext_p_ism_ap",td_drk.rk_planidtext_p_ism_ap,"BOOL_OP,OR,COMPOSITE_TEST,""""""<Unused>"""""",TEST_CLAUSE,TEST @Value(_filterValue) = td_drk.rk_planomrade_l",td_drk.rk_planomrade_l,"BOOL_OP,OR,COMPOSITE_TEST,""""""<Unused>"""""",TEST_CLAUSE,TEST @Value(_filterValue) = td_drk.rk_planomrade_l_ism_ap",td_drk.rk_planomrade_l_ism_ap,"BOOL_OP,OR,COMPOSITE_TEST,""""""<Unused>"""""",TEST_CLAUSE,TEST @Value(_filterValue) = td_drk.rk_rattighet_l",td_drk.rk_rattighet_l,"BOOL_OP,OR,COMPOSITE_TEST,""""""<Unused>"""""",TEST_CLAUSE,TEST @Value(_filterValue) = td_drk.rk_rattighet_l_ism_ap",td_drk.rk_rattighet_l_ism_ap,"BOOL_OP,OR,COMPOSITE_TEST,""""""<Unused>"""""",TEST_CLAUSE,TEST @Value(_filterValue) = td_drk.rk_rattighet_p",td_drk.rk_rattighet_p,"BOOL_OP,OR,COMPOSITE_TEST,""""""<Unused>"""""",TEST_CLAUSE,TEST @Value(_filterValue) = td_drk.rk_rattighet_p_ism_ap",td_drk.rk_rattighet_p_ism_ap,"BOOL_OP,OR,COMPOSITE_TEST,""""""<Unused>"""""",TEST_CLAUSE,TEST @Value(_filterValue) = td_drk.rk_rattighet_y",td_drk.rk_rattighet_y,"BOOL_OP,OR,COMPOSITE_TEST,""""""<Unused>"""""",TEST_CLAUSE,TEST @Value(_filterValue) = td_drk.rk_rattighet_y_ism_ap",td_drk.rk_rattighet_y_ism_ap,"BOOL_OP,OR,COMPOSITE_TEST,""""""<Unused>"""""",TEST_CLAUSE,TEST @Value(_filterValue) = td_drk.rk_rattighetid_p",td_drk.rk_rattighetid_p,"BOOL_OP,OR,COMPOSITE_TEST,""""""<Unused>"""""",TEST_CLAUSE,TEST @Value(_filterValue) = td_drk.rk_rattighetid_p_ism_ap",td_drk.rk_rattighetid_p_ism_ap,"BOOL_OP,OR,COMPOSITE_TEST,""""""<Unused>"""""",TEST_CLAUSE,TEST @Value(_filterValue) = td_drk.rk_rattighetidtext_p",td_drk.rk_rattighetidtext_p,"BOOL_OP,OR,COMPOSITE_TEST,""""""<Unused>"""""",TEST_CLAUSE,TEST @Value(_filterValue) = td_drk.rk_rattighetidtext_p_ism_ap",td_drk.rk_rattighetidtext_p_ism_ap,"BOOL_OP,OR,COMPOSITE_TEST,""""""<Unused>"""""",TEST_CLAUSE,TEST @Value(_filterValue) = td_drk.rk_rattighetomrade_l",td_drk.rk_rattighetomrade_l,"BOOL_OP,OR,COMPOSITE_TEST,""""""<Unused>"""""",TEST_CLAUSE,TEST @Value(_filterValue) = td_drk.rk_rattighetomrade_l_ism_ap",td_drk.rk_rattighetomrade_l_ism_ap,"BOOL_OP,OR,COMPOSITE_TEST,""""""<Unused>"""""",TEST_CLAUSE,TEST @Value(_filterValue) = td_drk.rk_rattighettext_p",td_drk.rk_rattighettext_p,"BOOL_OP,OR,COMPOSITE_TEST,""""""<Unused>"""""",TEST_CLAUSE,TEST @Value(_filterValue) = td_drk.rk_rattighettext_p_ism_ap",td_drk.rk_rattighettext_p_ism_ap
    td_drk.rk_3dfastighet_y -> 3D
    td_drk.rk_3dfastighet_y_ism_ap -> 3D [Input_2]
    td_drk.rk_3dfastighetid_p -> 3D [Input_3]
    td_drk.rk_3dfastighetid_p_ism_ap -> 3D [Input_4]
    td_drk.rk_3dfastighetidtext_p -> 3D [Input_5]
    td_drk.rk_3dfastighetidtext_p_ism_ap -> 3D [Input_6]
    td_drk.rk_3dfastighetomrade_l -> 3D [Input_7]
    td_drk.rk_3dfastighetomrade_l_ism_ap -> 3D [Input_8]
    td_drk.rk_bestammelse_l -> Bestammalese
    td_drk.rk_bestammelse_l_ism_ap -> Bestammalese [Input_2]
    td_drk.rk_bestammelse_y -> Bestammalese [Input_3]
    td_drk.rk_bestammelse_y_ism_ap -> Bestammalese [Input_4]
    td_drk.rk_bestammelseadmtext_p -> Bestammalese [Input_5]
    td_drk.rk_bestammelseadmtext_p_ism_ap -> Bestammalese [Input_6]
    td_drk.rk_bestammelseid_p -> Bestammalese [Input_7]
    td_drk.rk_bestammelseid_p_ism_ap -> Bestammalese [Input_8]
    td_drk.rk_bestammelseomrade_l -> Bestammalese [Input_9]
    td_drk.rk_bestammelseomrade_l_ism_ap -> Bestammalese [Input_10]
    td_drk.rk_bestammelsetext_p -> Bestammalese [Input_11]
    td_drk.rk_bestammelsetext_p_ism_ap -> Bestammalese [Input_12]
    td_drk.rk_fastighet_l -> Fastighet
    td_drk.rk_fastighet_l_ism_ap -> Fastighet [Input_2]
    td_drk.rk_fastighet_p -> Fastighet [Input_3]
    td_drk.rk_fastighet_p_ism_ap -> Fastighet [Input_4]
    td_drk.rk_fastighet_y -> Fastighet [Input_5]
    td_drk.rk_fastighet_y_ism_ap -> Fastighet [Input_6]
    td_drk.rk_fastighetadmtext_p -> Fastighet [Input_7]
    td_drk.rk_fastighetadmtext_p_ism_ap -> Fastighet [Input_8]
    td_drk.rk_fastighetgrans_l -> Fastighet [Input_9]
    td_drk.rk_fastighetgrans_l_ism_ap -> Fastighet [Input_10]
    td_drk.rk_fastighetid_p -> Fastighet [Input_11]
    td_drk.rk_fastighetid_p_ism_ap -> Fastighet [Input_12]
    td_drk.rk_fastighetidtext_p -> Fastighet [Input_13]
    td_drk.rk_fastighetidtext_p_ism_ap -> Fastighet [Input_14]
    td_drk.rk_fastighettext_p -> Fastighet [Input_15]
    td_drk.rk_fastighettext_p_ism_ap -> Fastighet [Input_16]
    td_drk.rk_ga_l -> GA
    td_drk.rk_ga_l_ism_ap -> GA [Input_2]
    td_drk.rk_ga_p -> GA [Input_3]
    td_drk.rk_ga_p_ism_ap -> GA [Input_4]
    td_drk.rk_ga_y -> GA [Input_5]
    td_drk.rk_ga_y_ism_ap -> GA [Input_6]
    td_drk.rk_gaomrade_l -> GA [Input_7]
    td_drk.rk_gaomrade_l_ism_ap -> GA [Input_8]
    td_drk.rk_gatext_p -> GA [Input_9]
    td_drk.rk_gatext_p_ism_ap -> GA [Input_10]
    td_drk.rk_granspunkt_p -> Fastighet [Input_17]
    td_drk.rk_granspunkt_p_ism_ap -> Fastighet [Input_18]
    td_drk.rk_plan_y -> Plan
    td_drk.rk_plan_y_ism_ap -> Plan [Input_2]
    td_drk.rk_planadmtext_p -> Plan [Input_3]
    td_drk.rk_planadmtext_p_ism_ap -> Plan [Input_4]
    td_drk.rk_planid_p -> Plan [Input_5]
    td_drk.rk_planid_p_ism_ap -> Plan [Input_6]
    td_drk.rk_planidtext_p -> Plan [Input_7]
    td_drk.rk_planidtext_p_ism_ap -> Plan [Input_8]
    td_drk.rk_planomrade_l -> Plan [Input_9]
    td_drk.rk_planomrade_l_ism_ap -> Plan [Input_10]
    td_drk.rk_rattighet_l -> Rättigheter
    td_drk.rk_rattighet_l_ism_ap -> Rättigheter [Input_2]
    td_drk.rk_rattighet_p -> Rättigheter [Input_3]
    td_drk.rk_rattighet_p_ism_ap -> Rättigheter [Input_4]
    td_drk.rk_rattighet_y -> Rättigheter [Input_5]
    td_drk.rk_rattighet_y_ism_ap -> Rättigheter [Input_6]
    td_drk.rk_rattighetid_p -> Rättigheter [Input_7]
    td_drk.rk_rattighetid_p_ism_ap -> Rättigheter [Input_8]
    td_drk.rk_rattighetidtext_p -> Rättigheter [Input_9]
    td_drk.rk_rattighetidtext_p_ism_ap -> Rättigheter [Input_10]
    td_drk.rk_rattighetomrade_l -> Rättigheter [Input_11]
    td_drk.rk_rattighetomrade_l_ism_ap -> Rättigheter [Input_12]
    td_drk.rk_rattighettext_p -> Rättigheter [Input_13]
    td_drk.rk_rattighettext_p_ism_ap -> Rättigheter [Input_14]
3D
    DATASET = @Value(Dataset)
    FME_FEATURE_TYPE_NAME = @Value(fme_feature_type_name)
    FME_FORMAT_SHORT_NAME = @Value(fme_format_short_name)
    OutSchemaFileNameSuffix = flush
    RotDirectory = ../
    _FILTERVALUE = @Value(_filterValue)
    -> vektor2vinklar
    <Rejected> -> Junction_11
Bestammalese
    DATASET = @Value(Dataset)
    FME_FEATURE_TYPE_NAME = @Value(fme_feature_type_name)
    FME_FORMAT_SHORT_NAME = @Value(fme_format_short_name)
    _FILTERVALUE = @Value(_filterValue)
    -> vektor2vinklar
    <Rejected> -> Junction_11
Fastighet
    DATASET = @Value(Dataset)
    FME_FEATURE_TYPE_NAME = @Value(fme_feature_type_name)
    FME_FORMAT_SHORT_NAME = @Value(fme_format_short_name)
    _FILTERVALUE = @Value(_filterValue)
    -> vektor2vinklar
    <Rejected> -> Junction_11
GA
    DATASET = @Value(Dataset)
    FME_FEATURE_TYPE_NAME = @Value(fme_feature_type_name)
    FME_FORMAT_SHORT_NAME = @Value(fme_format_short_name)
    _FILTERVALUE = @Value(_filterValue)
    -> vektor2vinklar
    Huvudobjekt -> SearchBoundingBoxAndPoint
    <Rejected> -> Junction_11
Plan
    DATASET = @Value(Dataset)
    FME_FEATURE_TYPE_NAME = @Value(fme_feature_type_name)
    FME_FORMAT_SHORT_NAME = @Value(fme_format_short_name)
    _FILTERVALUE = @Value(_filterValue)
    -> vektor2vinklar
    <Rejected> -> Junction_11
Rättigheter
    DATASET = @Value(Dataset)
    FME_FEATURE_TYPE_NAME = @Value(fme_feature_type_name)
    FME_FORMAT_SHORT_NAME = @Value(fme_format_short_name)
    _FILTERVALUE = @Value(_filterValue)
    -> vektor2vinklar
    Huvudobjekt -> SearchBoundingBoxAndPoint_2
    <Rejected> -> Junction_11
vektor2vinklar
    -> ArcStroker
Note: ArcStroker [ArcStroker] / General: / Stroke By: Maximum Deviation / Maximum Deviation: 0.02 / Make Polygon Out of 360 Degree Arcs: No
ArcStroker
    MAKE_POLY = No
    STROKE_CHOICE = Maximum Deviation
    TOLERANCE_VAL = 0.02
    STROKED -> 2DForcer
2DForcer
    2D -> GeometryRefiner
GeometryRefiner
    -> AttributeExposer
AttributeExposer
    ATTR_LIST = fme_feature_type
    -> AttributeCopier
AttributeCopier
    ATTR_TABLE = COPY fme_feature_type > _name
    -> StringReplacer
StringReplacer
    CASE = NO
    FIND_TEXT = (_p|_l|_y|_t)$
    NO_MATCH = _FME_NO_OP_
    REGEXP = YES
    SRC_ATTRS = _name
    -> StringReplacer_2
StringReplacer_2
    CASE = NO
    FIND_TEXT = ^td_drk.
    NO_MATCH = _FME_NO_OP_
    REGEXP = YES
    SRC_ATTRS = _name
    -> AttributeCreator_5
    -> Tester
AttributeCreator_5
    ATTR_TABLE = SET_TO _name_extension
    -> StringConcatenator_4
StringConcatenator_4
    ACTION = Create New Attribute
    PARM_LINE = @Value(_name)@Value(_name_extension)_p
    VAL_ATTR = DatasetName
    -> TestFilter_3
TestFilter_3
    DEFAULT_VALUE = <UNFILTERED>
    TEST_LIST = "BOOL_OP,OR,COMPOSITE_TEST,""""""<Unused>"""""",TEST_CLAUSE,TEST @Value(DatasetName) = rk_3dfastighet_y_ism_ap_p",rk_3dfastighet_y_ism_ap_p,"BOOL_OP,OR,COMPOSITE_TEST,""""""<Unused>"""""",TEST_CLAUSE,TEST @Value(DatasetName) = rk_3dfastighetid_p_ism_ap_p",rk_3dfastighetid_p_ism_ap_p,"BOOL_OP,OR,COMPOSITE_TEST,""""""<Unused>"""""",TEST_CLAUSE,TEST @Value(DatasetName) = rk_3dfastighetidtext_p_ism_ap_p",rk_3dfastighetidtext_p_ism_ap_p,"BOOL_OP,OR,COMPOSITE_TEST,""""""<Unused>"""""",TEST_CLAUSE,TEST @Value(DatasetName) = rk_3dfastighetomrade_l_ism_ap_p",rk_3dfastighetomrade_l_ism_ap_p,"BOOL_OP,OR,COMPOSITE_TEST,""""""<Unused>"""""",TEST_CLAUSE,TEST @Value(DatasetName) = rk_bestammelse_l_ism_ap_p",rk_bestammelse_l_ism_ap_p,"BOOL_OP,OR,COMPOSITE_TEST,""""""<Unused>"""""",TEST_CLAUSE,TEST @Value(DatasetName) = rk_bestammelse_y_ism_ap_p",rk_bestammelse_y_ism_ap_p,"BOOL_OP,OR,COMPOSITE_TEST,""""""<Unused>"""""",TEST_CLAUSE,TEST @Value(DatasetName) = rk_bestammelseadmtext_p_ism_ap_p",rk_bestammelseadmtext_p_ism_ap_p,"BOOL_OP,OR,COMPOSITE_TEST,""""""<Unused>"""""",TEST_CLAUSE,TEST @Value(DatasetName) = rk_bestammelseid_p_ism_ap_p",rk_bestammelseid_p_ism_ap_p,"BOOL_OP,OR,COMPOSITE_TEST,""""""<Unused>"""""",TEST_CLAUSE,TEST @Value(DatasetName) = rk_bestammelseomrade_l_ism_ap_p",rk_bestammelseomrade_l_ism_ap_p,"BOOL_OP,OR,COMPOSITE_TEST,""""""<Unused>"""""",TEST_CLAUSE,TEST @Value(DatasetName) = rk_bestammelsetext_p_ism_ap_p",rk_bestammelsetext_p_ism_ap_p,"BOOL_OP,OR,COMPOSITE_TEST,""""""<Unused>"""""",TEST_CLAUSE,TEST @Value(DatasetName) = rk_fastighet_l_ism_ap_p",rk_fastighet_l_ism_ap_p,"BOOL_OP,OR,COMPOSITE_TEST,""""""<Unused>"""""",TEST_CLAUSE,TEST @Value(DatasetName) = rk_fastighet_p_ism_ap_p",rk_fastighet_p_ism_ap_p,"BOOL_OP,OR,COMPOSITE_TEST,""""""<Unused>"""""",TEST_CLAUSE,TEST @Value(DatasetName) = rk_fastighet_y_ism_ap_p",rk_fastighet_y_ism_ap_p,"BOOL_OP,OR,COMPOSITE_TEST,""""""<Unused>"""""",TEST_CLAUSE,TEST @Value(DatasetName) = rk_fastighetadmtext_p_ism_ap_p",rk_fastighetadmtext_p_ism_ap_p,"BOOL_OP,OR,COMPOSITE_TEST,""""""<Unused>"""""",TEST_CLAUSE,TEST @Value(DatasetName) = rk_fastighetgrans_l_ism_ap_p",rk_fastighetgrans_l_ism_ap_p,"BOOL_OP,OR,COMPOSITE_TEST,""""""<Unused>"""""",TEST_CLAUSE,TEST @Value(DatasetName) = rk_fastighetid_p_ism_ap_p",rk_fastighetid_p_ism_ap_p,"BOOL_OP,OR,COMPOSITE_TEST,""""""<Unused>"""""",TEST_CLAUSE,TEST @Value(DatasetName) = rk_fastighetidtext_p_ism_ap_p",rk_fastighetidtext_p_ism_ap_p,"BOOL_OP,OR,COMPOSITE_TEST,""""""<Unused>"""""",TEST_CLAUSE,TEST @Value(DatasetName) = rk_fastighettext_p_ism_ap_p",rk_fastighettext_p_ism_ap_p,"BOOL_OP,OR,COMPOSITE_TEST,""""""<Unused>"""""",TEST_CLAUSE,TEST @Value(DatasetName) = rk_ga_l_ism_ap_p",rk_ga_l_ism_ap_p,"BOOL_OP,OR,COMPOSITE_TEST,""""""<Unused>"""""",TEST_CLAUSE,TEST @Value(DatasetName) = rk_ga_p_ism_ap_p",rk_ga_p_ism_ap_p,"BOOL_OP,OR,COMPOSITE_TEST,""""""<Unused>"""""",TEST_CLAUSE,TEST @Value(DatasetName) = rk_ga_y_ism_ap_p",rk_ga_y_ism_ap_p,"BOOL_OP,OR,COMPOSITE_TEST,""""""<Unused>"""""",TEST_CLAUSE,TEST @Value(DatasetName) = rk_gaomrade_l_ism_ap_p",rk_gaomrade_l_ism_ap_p,"BOOL_OP,OR,COMPOSITE_TEST,""""""<Unused>"""""",TEST_CLAUSE,TEST @Value(DatasetName) = rk_gatext_p_ism_ap_p",rk_gatext_p_ism_ap_p,"BOOL_OP,OR,COMPOSITE_TEST,""""""<Unused>"""""",TEST_CLAUSE,TEST @Value(DatasetName) = rk_granspunkt_p_ism_ap_p",rk_granspunkt_p_ism_ap_p,"BOOL_OP,OR,COMPOSITE_TEST,""""""<Unused>"""""",TEST_CLAUSE,TEST @Value(DatasetName) = rk_plan_y_ism_ap_p",rk_plan_y_ism_ap_p,"BOOL_OP,OR,COMPOSITE_TEST,""""""<Unused>"""""",TEST_CLAUSE,TEST @Value(DatasetName) = rk_planadmtext_p_ism_ap_p",rk_planadmtext_p_ism_ap_p,"BOOL_OP,OR,COMPOSITE_TEST,""""""<Unused>"""""",TEST_CLAUSE,TEST @Value(DatasetName) = rk_planid_p_ism_ap_p",rk_planid_p_ism_ap_p,"BOOL_OP,OR,COMPOSITE_TEST,""""""<Unused>"""""",TEST_CLAUSE,TEST @Value(DatasetName) = rk_planidtext_p_ism_ap_p",rk_planidtext_p_ism_ap_p,"BOOL_OP,OR,COMPOSITE_TEST,""""""<Unused>"""""",TEST_CLAUSE,TEST @Value(DatasetName) = rk_planomrade_l_ism_ap_p",rk_planomrade_l_ism_ap_p,"BOOL_OP,OR,COMPOSITE_TEST,""""""<Unused>"""""",TEST_CLAUSE,TEST @Value(DatasetName) = rk_rattighet_l_ism_ap_p",rk_rattighet_l_ism_ap_p,"BOOL_OP,OR,COMPOSITE_TEST,""""""<Unused>"""""",TEST_CLAUSE,TEST @Value(DatasetName) = rk_rattighet_p_ism_ap_p",rk_rattighet_p_ism_ap_p,"BOOL_OP,OR,COMPOSITE_TEST,""""""<Unused>"""""",TEST_CLAUSE,TEST @Value(DatasetName) = rk_rattighet_y_ism_ap_p",rk_rattighet_y_ism_ap_p,"BOOL_OP,OR,COMPOSITE_TEST,""""""<Unused>"""""",TEST_CLAUSE,TEST @Value(DatasetName) = rk_rattighetid_p_ism_ap_p",rk_rattighetid_p_ism_ap_p,"BOOL_OP,OR,COMPOSITE_TEST,""""""<Unused>"""""",TEST_CLAUSE,TEST @Value(DatasetName) = rk_rattighetidtext_p_ism_ap_p",rk_rattighetidtext_p_ism_ap_p,"BOOL_OP,OR,COMPOSITE_TEST,""""""<Unused>"""""",TEST_CLAUSE,TEST @Value(DatasetName) = rk_rattighetomrade_l_ism_ap_p",rk_rattighetomrade_l_ism_ap_p,"BOOL_OP,OR,COMPOSITE_TEST,""""""<Unused>"""""",TEST_CLAUSE,TEST @Value(DatasetName) = rk_rattighettext_p_ism_ap_p",rk_rattighettext_p_ism_ap_p
    rk_3dfastighet_y_ism_ap_p -> AttributeKeeper
    rk_3dfastighetid_p_ism_ap_p -> AttributeKeeper
    rk_3dfastighetidtext_p_ism_ap_p -> AttributeKeeper_7
    rk_3dfastighetomrade_l_ism_ap_p -> AttributeKeeper_2
    rk_bestammelse_l_ism_ap_p -> AttributeKeeper_3
    rk_bestammelse_y_ism_ap_p -> AttributeKeeper_3
    rk_bestammelseadmtext_p_ism_ap_p -> AttributeKeeper_6
    rk_bestammelseid_p_ism_ap_p -> AttributeKeeper_3
    rk_bestammelseomrade_l_ism_ap_p -> AttributeKeeper_2
    rk_bestammelsetext_p_ism_ap_p -> AttributeKeeper_6
    rk_fastighet_l_ism_ap_p -> AttributeKeeper_4
    rk_fastighet_p_ism_ap_p -> AttributeKeeper_4
    rk_fastighet_y_ism_ap_p -> AttributeKeeper_4
    rk_fastighetadmtext_p_ism_ap_p -> AttributeKeeper_6
    rk_fastighetgrans_l_ism_ap_p -> AttributeKeeper_2
    rk_fastighetid_p_ism_ap_p -> AttributeKeeper_10
    rk_fastighetidtext_p_ism_ap_p -> AttributeKeeper_11
    rk_fastighettext_p_ism_ap_p -> AttributeKeeper_11
    rk_ga_l_ism_ap_p -> AttributeKeeper_13
    rk_ga_p_ism_ap_p -> AttributeKeeper_13
    rk_ga_y_ism_ap_p -> AttributeKeeper_13
    rk_gaomrade_l_ism_ap_p -> AttributeKeeper_2
    rk_gatext_p_ism_ap_p -> AttributeKeeper_6
    rk_granspunkt_p_ism_ap_p -> AttributeKeeper_12
    rk_plan_y_ism_ap_p -> AttributeKeeper_3
    rk_planadmtext_p_ism_ap_p -> AttributeKeeper_6
    rk_planid_p_ism_ap_p -> AttributeKeeper_3
    rk_planidtext_p_ism_ap_p -> AttributeKeeper_6
    rk_planomrade_l_ism_ap_p -> AttributeKeeper_2
    rk_rattighet_l_ism_ap_p -> AttributeKeeper_12
    rk_rattighet_p_ism_ap_p -> AttributeKeeper_12
    rk_rattighet_y_ism_ap_p -> AttributeKeeper_12
    rk_rattighetid_p_ism_ap_p -> AttributeKeeper_3
    rk_rattighetidtext_p_ism_ap_p -> AttributeKeeper_5
    rk_rattighetomrade_l_ism_ap_p -> AttributeKeeper_2
    rk_rattighettext_p_ism_ap_p -> AttributeKeeper_6
AttributeKeeper
    CREATE_BULK_MODE_FEATURES = No
    KEEP_ATTRS = rk_tillagg,grader,rk_omrade,rk_fastighet,rk_block_enhet,radianer,rk_dep,gon,rk_trakt,DatasetName
    -> fastighet_y (writer ESRISHAPE_1)
    -> Junction_12
    -> fastighet_y (writer SDF3_1)
    -> schema (writer POSTGIS_1)
    -> Table1 (writer POSTGIS_14)
    -> Shapefile1 (writer SHAPEFILE_1)
Note: <@Value(DatasetName)>: [SHAPEFILE]
Shapefile1 (writer SHAPEFILE_1)
    attributes: rk_dep char(200), rk_trakt char(200), rk_block_e char(200), rk_fastigh char(200), rk_omrade char(200), rk_tillagg char(200), radianer double, grader double, gon double
fastighet_y (writer ESRISHAPE_1) [off]
    attributes: rk_trakt char(200), rk_block_e char(200), rk_omrade char(200), rk_tillagg char(200), rk_fastigh char(200), rk_dep char(200), radianer char(200), grader char(200), gon char(200)
schema (writer POSTGIS_1)
    attributes: rk_trakt varchar(200), rk_block_enhet varchar(200), rk_omrade varchar(200), rk_tillagg varchar(200), rk_fastighet varchar(200), rk_dep varchar(200), radianer float8, grader float8, gon float8
fastighet_y (writer SDF3_1)
    attributes: rk_trakt char(200), rk_block_enhet char(200), rk_omrade char(200), rk_tillagg char(200), rk_fastighet char(200), rk_dep char(200), radianer char(200), grader char(200), gon char(200)
Table1 (writer POSTGIS_14)
    attributes: rk_dep varchar(200), rk_trakt varchar(200), rk_block_enhet varchar(200), rk_omrade varchar(200), rk_tillagg varchar(200), rk_fastighet varchar(200), radianer float8, grader float8, gon float8
AttributeKeeper_7
    CREATE_BULK_MODE_FEATURES = No
    KEEP_ATTRS = rk_trakt,grader,rk_tillagg,rk_block_enhet,rk_dep,gon,DatasetName,radianer,rk_omrade
    -> fastighet_y0003 (writer SDF3_1)
    -> fastighet_y0003 (writer ESRISHAPE_1)
    -> Junction_12
    -> Table1 (writer POSTGIS_2)
    -> Table1 (writer POSTGIS_15)
    -> Shapefile100 (writer SHAPEFILE_1)
fastighet_y0003 (writer ESRISHAPE_1) [off]
    attributes: rk_trakt char(200), rk_block_e char(200), rk_omrade char(200), rk_tillagg char(200), rk_dep char(200), radianer char(200), grader char(200), gon char(200)
Table1 (writer POSTGIS_2)
    attributes: rk_trakt varchar(200), rk_block_enhet varchar(200), rk_omrade varchar(200), rk_tillagg varchar(200), rk_dep varchar(200), radianer float8, grader float8, gon float8
fastighet_y0003 (writer SDF3_1)
    attributes: rk_trakt char(200), rk_block_enhet char(200), rk_omrade char(200), rk_tillagg char(200), rk_dep char(200), radianer char(200), grader char(200), gon char(200)
Table1 (writer POSTGIS_15)
    attributes: rk_dep varchar(200), rk_trakt varchar(200), rk_block_enhet varchar(200), rk_omrade varchar(200), rk_tillagg varchar(200), radianer float8, grader float8, gon float8
Note: <@Value(DatasetName)>: [SHAPEFILE]
Shapefile100 (writer SHAPEFILE_1)
    attributes: rk_dep char(200), rk_trakt char(200), rk_block_e char(200), rk_omrade char(200), rk_tillagg char(200), radianer double, grader double, gon double
AttributeKeeper_2
    CREATE_BULK_MODE_FEATURES = No
    KEEP_ATTRS = grader,rk_xyfel,radianer,rk_dep,gon,DatasetName
    -> Junction_12
    -> fastighet_y00 (writer ESRISHAPE_1)
    -> fastighet_y00 (writer SDF3_1)
    -> Table1 (writer POSTGIS_3)
    -> Table1 (writer POSTGIS_16)
    -> Shapefile10000 (writer SHAPEFILE_1)
fastighet_y00 (writer ESRISHAPE_1) [off]
    attributes: rk_dep char(200), rk_xyfel char(200), radianer char(200), grader char(200), gon char(200)
Table1 (writer POSTGIS_3)
    attributes: rk_dep varchar(200), rk_xyfel varchar(200), radianer float8, grader float8, gon float8
fastighet_y00 (writer SDF3_1)
    attributes: rk_dep char(200), rk_xyfel char(200), radianer char(200), grader char(200), gon char(200)
Table1 (writer POSTGIS_16)
    attributes: rk_dep varchar(200), rk_xyfel varchar(200), radianer float8, grader float8, gon float8, datasetname text
Note: <@Value(DatasetName)>: [SHAPEFILE]
Shapefile10000 (writer SHAPEFILE_1)
    attributes: rk_dep char(200), rk_xyfel char(200), radianer double, grader double, gon double
AttributeKeeper_3
    CREATE_BULK_MODE_FEATURES = No
    KEEP_ATTRS = grader,rk_dep,rk_extid,gon,DatasetName,radianer
    -> fastighet_y0000 (writer ESRISHAPE_1)
    -> fastighet_y0000 (writer SDF3_1)
    -> Junction_12
    -> Table1 (writer POSTGIS_4)
    -> Table1 (writer POSTGIS_17)
    -> Shapefile1000000 (writer SHAPEFILE_1)
fastighet_y0000 (writer ESRISHAPE_1) [off]
    attributes: rk_dep char(200), rk_extid char(200), radianer char(200), grader char(200), gon char(200)
Table1 (writer POSTGIS_4)
    attributes: rk_dep varchar(200), rk_extid varchar(200), radianer float8, grader float8, gon float8
fastighet_y0000 (writer SDF3_1)
    attributes: rk_dep char(200), rk_extid char(200), radianer char(200), grader char(200), gon char(200)
Table1 (writer POSTGIS_17)
    attributes: rk_dep varchar(200), rk_extid varchar(200), radianer float8, grader float8, gon float8, datasetname text
Note: <@Value(DatasetName)>: [SHAPEFILE]
Shapefile1000000 (writer SHAPEFILE_1)
    attributes: rk_dep char(200), rk_extid char(200), radianer double, grader double, gon double
AttributeKeeper_4
    CREATE_BULK_MODE_FEATURES = No
    KEEP_ATTRS = rk_trakt,grader,rk_tillagg,rk_block_enhet,rk_dep,rk_fastighet,gon,DatasetName,radianer,rk_omrade
    -> fastighet_y0001 (writer ESRISHAPE_1)
    -> fastighet_y0001 (writer SDF3_1)
    -> Junction_12
    -> Table1 (writer POSTGIS_6)
    -> Table1 (writer POSTGIS_18)
    -> Shapefile1000001 (writer SHAPEFILE_1)
fastighet_y0001 (writer ESRISHAPE_1) [off]
    attributes: rk_dep char(200), rk_trakt char(200), rk_block_e char(200), rk_omrade char(200), rk_tillagg char(200), rk_fastigh char(200), radianer char(200), grader char(200), gon char(200)
Table1 (writer POSTGIS_6)
    attributes: rk_dep varchar(200), rk_trakt varchar(200), rk_block_enhet varchar(200), rk_omrade varchar(200), rk_tillagg varchar(200), rk_fastighet varchar(200), radianer float8, grader float8, gon float8
fastighet_y0001 (writer SDF3_1)
    attributes: rk_dep char(200), rk_trakt char(200), rk_block_enhet char(200), rk_omrade char(200), rk_tillagg char(200), rk_fastighet char(200), radianer char(200), grader char(200), gon char(200)
Table1 (writer POSTGIS_18)
    attributes: rk_fastighet varchar(200), rk_dep varchar(200), rk_trakt varchar(200), rk_block_enhet varchar(200), rk_omrade varchar(200), rk_tillagg varchar(200), radianer float8, grader float8, gon float8, datasetname text
Note: <@Value(DatasetName)>: [SHAPEFILE]
Shapefile1000001 (writer SHAPEFILE_1)
    attributes: rk_dep char(200), rk_trakt char(200), rk_block_e char(200), rk_fastigh char(200), rk_omrade char(200), rk_tillagg char(200), radianer double, grader double, gon double
AttributeKeeper_6
    CREATE_BULK_MODE_FEATURES = No
    KEEP_ATTRS = grader,rk_text,rk_dep,gon,DatasetName,radianer
    -> fastighet_y000000 (writer ESRISHAPE_1)
    -> fastighet_y000000 (writer SDF3_1)
    -> Junction_12
    -> Table1 (writer POSTGIS_5)
    -> Table1 (writer POSTGIS_19)
    -> Shapefile1000002 (writer SHAPEFILE_1)
fastighet_y000000 (writer ESRISHAPE_1) [off]
    attributes: rk_dep char(200), rk_text char(200), radianer char(200), grader char(200), gon char(200)
Table1 (writer POSTGIS_5)
    attributes: rk_dep varchar(200), rk_text varchar(200), radianer float8, grader float8, gon float8
fastighet_y000000 (writer SDF3_1)
    attributes: rk_dep char(200), rk_text char(200), radianer char(200), grader char(200), gon char(200)
Table1 (writer POSTGIS_19)
    attributes: rk_dep varchar(200), rk_text varchar(200), radianer float8, grader float8, gon float8
Note: <@Value(DatasetName)>: [SHAPEFILE]
Shapefile1000002 (writer SHAPEFILE_1)
    attributes: rk_dep char(200), rk_text char(200), radianer double, grader double, gon double
AttributeKeeper_13
    CREATE_BULK_MODE_FEATURES = No
    KEEP_ATTRS = rk_trakt,grader,rk_block_enhet,rk_dep,rk_fastighet,gon,DatasetName,radianer
    -> fastighet_y000100 (writer ESRISHAPE_1)
    -> fastighet_y000100 (writer SDF3_1)
    -> Junction_12
    -> Table1 (writer POSTGIS_7)
    -> Table1 (writer POSTGIS_20)
    -> Shapefile1000003 (writer SHAPEFILE_1)
fastighet_y000100 (writer ESRISHAPE_1) [off]
    attributes: rk_dep char(200), rk_trakt char(200), rk_block_e char(200), rk_fastigh char(200), radianer char(200), grader char(200), gon char(200)
Table1 (writer POSTGIS_7)
    attributes: rk_dep varchar(200), rk_trakt varchar(200), rk_block_enhet varchar(200), rk_fastighet varchar(200), radianer float8, grader float8, gon float8
fastighet_y000100 (writer SDF3_1)
    attributes: rk_dep char(200), rk_trakt char(200), rk_block_enhet char(200), rk_fastighet char(200), radianer char(200), grader char(200), gon char(200)
Table1 (writer POSTGIS_20)
    attributes: rk_dep varchar(200), rk_trakt varchar(200), rk_block_enhet varchar(200), rk_fastighet varchar(200), radianer float8, grader float8, gon float8
Note: <@Value(DatasetName)>: [SHAPEFILE]
Shapefile1000003 (writer SHAPEFILE_1)
    attributes: rk_dep char(200), rk_trakt char(200), rk_block_e char(200), rk_fastigh char(200), radianer double, grader double, gon double
AttributeKeeper_10
    CREATE_BULK_MODE_FEATURES = No
    KEEP_ATTRS = rk_trakt,grader,rk_block_enhet,rk_dep,rk_fastighet,gon,DatasetName,radianer,rk_omrade
    -> fastighet_y000200 (writer ESRISHAPE_1)
    -> fastighet_y000200 (writer SDF3_1)
    -> Junction_12
    -> Table1 (writer POSTGIS_8)
    -> Table1 (writer POSTGIS_21)
    -> Shapefile1000004 (writer SHAPEFILE_1)
fastighet_y000200 (writer ESRISHAPE_1) [off]
    attributes: rk_dep char(200), rk_trakt char(200), rk_block_e char(200), rk_omrade char(200), rk_fastigh char(200), radianer char(200), grader char(200), gon char(200)
Table1 (writer POSTGIS_8)
    attributes: rk_dep varchar(200), rk_trakt varchar(200), rk_block_enhet varchar(200), rk_omrade varchar(200), rk_fastighet varchar(200), radianer float8, grader float8, gon float8
Note: <@Value(DatasetName)>: [SHAPEFILE]
Shapefile1000004 (writer SHAPEFILE_1)
    attributes: rk_dep char(200), rk_trakt char(200), rk_block_e char(200), rk_fastigh char(200), rk_omrade char(200), radianer double, grader double, gon double
fastighet_y000200 (writer SDF3_1)
    attributes: rk_dep char(200), rk_trakt char(200), rk_block_enhet char(200), rk_omrade char(200), rk_fastighet char(200), radianer char(200), grader char(200), gon char(200)
Table1 (writer POSTGIS_21)
    attributes: rk_dep varchar(200), rk_trakt varchar(200), rk_block_enhet varchar(200), rk_omrade varchar(200), rk_fastighet varchar(200), radianer float8, grader float8, gon float8
AttributeKeeper_11
    CREATE_BULK_MODE_FEATURES = No
    KEEP_ATTRS = rk_trakt,grader,rk_tillagg,rk_block_enhet,rk_dep,gon,DatasetName,radianer,rk_omrade
    -> fastighet_y000101 (writer ESRISHAPE_1)
    -> fastighet_y000101 (writer SDF3_1)
    -> Junction_12
    -> Table1 (writer POSTGIS_9)
    -> Table1 (writer POSTGIS_22)
    -> Shapefile1000005 (writer SHAPEFILE_1)
fastighet_y000101 (writer ESRISHAPE_1) [off]
    attributes: rk_dep char(200), rk_trakt char(200), rk_block_e char(200), rk_omrade char(200), rk_tillagg char(200), radianer char(200), grader char(200), gon char(200)
Table1 (writer POSTGIS_9)
    attributes: rk_dep varchar(200), rk_trakt varchar(200), rk_block_enhet varchar(200), rk_omrade varchar(200), rk_tillagg varchar(200), radianer float8, grader float8, gon float8
Note: <@Value(DatasetName)>: [SHAPEFILE]
Shapefile1000005 (writer SHAPEFILE_1)
    attributes: rk_dep char(200), rk_trakt char(200), rk_block_e char(200), rk_omrade char(200), rk_tillagg char(200), radianer double, grader double, gon double
fastighet_y000101 (writer SDF3_1)
    attributes: rk_dep char(200), rk_trakt char(200), rk_block_enhet char(200), rk_omrade char(200), rk_tillagg char(200), radianer char(200), grader char(200), gon char(200)
Table1 (writer POSTGIS_22)
    attributes: rk_dep varchar(200), rk_trakt varchar(200), rk_block_enhet varchar(200), rk_omrade varchar(200), rk_tillagg varchar(200), radianer float8, grader float8, gon float8
AttributeKeeper_12
    CREATE_BULK_MODE_FEATURES = No
    KEEP_ATTRS = grader,rk_dep,rk_extid,rk_xyfel,gon,DatasetName,radianer
    -> fastighet_y000201 (writer ESRISHAPE_1)
    -> fastighet_y000201 (writer SDF3_1)
    -> Junction_12
    -> Table1 (writer POSTGIS_10)
    -> Table1 (writer POSTGIS_23)
    -> Shapefile1000006 (writer SHAPEFILE_1)
Note: <@Value(DatasetName)>: [SHAPEFILE]
Shapefile1000006 (writer SHAPEFILE_1)
    attributes: rk_dep char(200), rk_xyfel char(200), rk_extid char(200), radianer double, grader double, gon double
fastighet_y000201 (writer ESRISHAPE_1) [off]
    attributes: rk_dep char(200), rk_extid char(200), rk_xyfel char(200), radianer char(200), grader char(200), gon char(200)
Table1 (writer POSTGIS_10)
    attributes: rk_dep varchar(200), rk_xyfel varchar(200), rk_extid varchar(200), radianer float8, grader float8, gon float8
fastighet_y000201 (writer SDF3_1)
    attributes: rk_dep char(200), rk_extid char(200), rk_xyfel char(200), radianer char(200), grader char(200), gon char(200)
Table1 (writer POSTGIS_23)
    attributes: rk_dep varchar(200), rk_extid varchar(200), rk_xyfel varchar(200), radianer float8, grader float8, gon float8
AttributeKeeper_5
    CREATE_BULK_MODE_FEATURES = No
    KEEP_ATTRS = rk_trakt,grader,rk_block_enhet,rk_text,rk_dep,gon,DatasetName,radianer
    -> fastighet_y000001 (writer ESRISHAPE_1)
    -> fastighet_y000001 (writer SDF3_1)
    -> Junction_12
    -> Table1 (writer POSTGIS_11)
    -> Table1 (writer POSTGIS_24)
    -> Shapefile1000007 (writer SHAPEFILE_1)
Junction_12
    -> Aggregator
fastighet_y000001 (writer ESRISHAPE_1) [off]
    attributes: rk_dep char(200), rk_text char(200), rk_trakt char(200), rk_block_e char(200), radianer char(200), grader char(200), gon char(200)
fastighet_y000001 (writer SDF3_1)
    attributes: rk_dep char(200), rk_text char(200), rk_trakt char(200), rk_block_enhet char(200), radianer char(200), grader char(200), gon char(200)
Table1 (writer POSTGIS_11)
    attributes: rk_dep varchar(200), rk_text varchar(200), rk_trakt varchar(200), rk_block_enhet varchar(200), radianer float8, grader float8, gon float8
Note: <@Value(DatasetName)>: [SHAPEFILE]
Shapefile1000007 (writer SHAPEFILE_1)
    attributes: rk_dep char(200), rk_trakt char(200), rk_block_e char(200), rk_text char(200), radianer double, grader double, gon double
Table1 (writer POSTGIS_24)
    attributes: rk_dep varchar(200), rk_text varchar(200), rk_trakt varchar(200), rk_block_enhet varchar(200), radianer float8, grader float8, gon float8
Junction_11
    -> Aggregator_6

Bookmark: Loggning
Note: AttributeCreator_12_-_FeatureMerger_3
Junction_2
    -> FeatureMerger_2 [SUPPLIER]
Note: AttributeCreator_12_-_FeatureMerger_3
Junction_4
    -> FeatureMerger_3 [SUPPLIER]
Junction_10
    -> FeatureMerger_6 [SUPPLIER]
Junction_8
    -> FeatureMerger_5 [SUPPLIER]
Note: Junction_11 : Output
Junction_15
    -> Junction_6
Junction_6
    -> FeatureMerger_4 [SUPPLIER]
Junction_17
    -> FeatureMerger_7 [SUPPLIER]
Junction_19
    -> FeatureMerger_8 [SUPPLIER]
Aggregator_5
    ACCUM_ATTRS_NAME = Use Attributes From One Feature
    AGGREGATE_TYPE = Homogeneous Collection (If Possible)
    CONCAT_ATTRS = error_msg
    COUNT_ATTR = Antal
    GROUP_BY = error_msg
    MODE = Geometry - Assemble One Level
    ORDERED = No
    SEP = "\n"
    AGGREGATE -> FeatureMerger_5 [REQUESTOR]
FeatureMerger_5
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_9
StringConcatenator_9
    ACTION = Create New Attribute
    PARM_LINE = fme_basicstring:49%17:Fel uppstod i försök att skapa sökgeometri. Fel: @Value(error_msg)
    VAL_ATTR = Logg
    -> DTStamperYYYY-MM-DD_HH:MI:SS.sss_4
DTStamperYYYY-MM-DD_HH:MI:SS.sss_4
    -> Logg_6
Logg_6: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Aggregator_7
    ACCUM_ATTRS_NAME = Use Attributes From One Feature
    AGGREGATE_TYPE = Homogeneous Collection (If Possible)
    GROUP_BY = fme_type
    MODE = Geometry - Assemble One Level
    ORDERED = No
    AGGREGATE -> Aggregator_8
Aggregator_8
    ACCUM_ATTRS_NAME = Use Attributes From One Feature
    AGGREGATE_TYPE = Homogeneous Collection (If Possible)
    CONCAT_ATTRS = fme_type
    MODE = Geometry - Assemble One Level
    ORDERED = No
    SEP = ", "
    AGGREGATE -> FeatureMerger_7 [REQUESTOR]
FeatureMerger_7
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_10
StringConcatenator_10
    ACTION = Create New Attribute
    PARM_LINE = fme_basicstring:59%16:Förekomst av oväntad geometrityp bland sökgeometrier. Fel: @Value(fme_type)
    VAL_ATTR = Logg
    -> DTStamperYYYY-MM-DD_HH:MI:SS.sss_6
DTStamperYYYY-MM-DD_HH:MI:SS.sss_6
    -> Logg_7
Logg_7: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Aggregator_10
    ACCUM_ATTRS_NAME = Use Attributes From One Feature
    AGGREGATE_TYPE = Homogeneous Collection (If Possible)
    COUNT_ATTR = antal
    MODE = Geometry - Assemble One Level
    ORDERED = No
    SEP = ", "
    AGGREGATE -> FeatureMerger_8 [REQUESTOR]
FeatureMerger_8
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_11
StringConcatenator_11
    ACTION = Create New Attribute
    PARM_LINE = fme_basicstring:41%13%6:Förekomst av oväntad typ av information (@Value(antal) st.).
    VAL_ATTR = Logg
    -> DTStamperYYYY-MM-DD_HH:MI:SS.sss_7
DTStamperYYYY-MM-DD_HH:MI:SS.sss_7
    -> Logg_8
Logg_8: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,VARNING,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Aggregator
    ACCUM_ATTRS_NAME = Use Attributes From One Feature
    AGGREGATE_TYPE = Homogeneous Collection (If Possible)
    COUNT_ATTR = Antal
    MODE = Geometry - Assemble One Level
    ORDERED = No
    SEP = ,
    AGGREGATE -> FeatureMerger_6 [REQUESTOR]
FeatureMerger_6
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_5
StringConcatenator_5
    ACTION = Create New Attribute
    PARM_LINE = Process @Value(ProcessName) har färdigbehandlat @Value(Antal) st. objekt.
    VAL_ATTR = Logg
    -> DTStamperYYYY-MM-DD_HH:MI:SS.sss_5
DTStamperYYYY-MM-DD_HH:MI:SS.sss_5
    -> Logg_5
Logg_5: WorkspaceRunner
    BLOCKING = No
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,KLART,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Aggregator_6
    ACCUM_ATTRS_NAME = Use Attributes From One Feature
    AGGREGATE_TYPE = Homogeneous Collection (If Possible)
    COUNT_ATTR = Antal
    GROUP_BY = error_msg
    MODE = Geometry - Assemble One Level
    ORDERED = No
    SEP = ", "
    AGGREGATE -> FeatureMerger_4 [REQUESTOR]
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_3
StringConcatenator_3
    ACTION = Create New Attribute
    PARM_LINE = Texter kunde inte hämtas eller FeatureMerge av objekt och text ej möjlig. Fel: @Value(error_msg)
    VAL_ATTR = Logg
    -> DTStamperYYYY-MM-DD_HH:MI:SS.sss_3
DTStamperYYYY-MM-DD_HH:MI:SS.sss_3
    -> Logg_4
Logg_4: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: Följande kolumn förekommer fler än / en gång för specifikt dataset
Aggregator_4
    ACCUM_ATTRS_NAME = Use Attributes From One Feature
    AGGREGATE_TYPE = Homogeneous Collection (If Possible)
    COUNT_ATTR = Antal
    GROUP_BY = dl_new_column_name
    MODE = Geometry - Assemble One Level
    ORDERED = No
    SEP = ", "
    AGGREGATE -> FeatureMerger_3 [REQUESTOR]
FeatureMerger_3
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_6
StringConcatenator_6
    ACTION = Create New Attribute
    PARM_LINE = Följande @Value(Antal)  st. kolumner finns det dubbletter för (@Value(dl_new_column_name)). För att exporterad data vara läsbar enligt manifest, ändra kolumnnamn i manifest.
    VAL_ATTR = Logg
    -> DTStamperYYYY-MM-DD_HH:MI:SS.sss_2
DTStamperYYYY-MM-DD_HH:MI:SS.sss_2
    -> Logg_3
Logg_3: WorkspaceRunner
    BLOCKING = Yes
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
Note: Endast som signal att starta logg
Sampler_2
    RATE = 1
    SAMPLE_MODE = No
    SAMPLE_TYPE_LONG = First N Features
    SAMPLED -> FeatureMerger_2 [REQUESTOR]
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_2
StringConcatenator_2
    ACTION = Create New Attribute
    PARM_LINE = Kör @Value(ProcessName) för data definierad i "$(SchemaFlush)" till datalagret.
    VAL_ATTR = Logg
    -> DTStamperYYYY-MM-DD_HH:MI:SS.sss
DTStamperYYYY-MM-DD_HH:MI:SS.sss
    -> Logg_2
Logg_2: WorkspaceRunner
    BLOCKING = No
    WORKSPACE_FILE = C:\dev\Datalager_procsrc\_sys\_logg.fmw
    WORKSPACE_PARAMETERS = EX_DATE_TIME,@Value(_datetimestamp),EX_PROCESS_NAME,@Value(ProcessName),EX_ID,@Value(ProcessID),EX_TYPE,INFORMATION,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)

Bookmark: Sökunderlag
SearchBoundingBoxAndPoint
    ATTRIBUTES = rk_fastighet
    RotDirectory = ../
    BoundingBox -> AttributeCreator_6
    point -> 2DForcer
    <Rejected> -> Aggregator_5
AttributeCreator_6
    ATTR_TABLE = SET_TO fme_feature_type = rk_ga
    -> Junction_5
SearchBoundingBoxAndPoint_2
    ATTRIBUTES = rk_extid
    RotDirectory = ../
    BoundingBox -> AttributeCreator_8
    point -> 2DForcer
    <Rejected> -> Aggregator_5
AttributeCreator_8
    ATTR_TABLE = SET_TO fme_feature_type = rk_rattighet
    -> Junction_5
Junction_5
    -> ArcStroker
Tester
    BOOL_OP = OR
    COMPOSITE_TEST = 1 OR 2
    TEST_CLAUSE:
      TEST @Value(_name) = rk_ga
      TEST @Value(_name) = rk_rattighet
    TEST_MODE = TEST
    PASSED -> TestFilter_4
Note: yta linje eller punkt
TestFilter_4
    DEFAULT_VALUE = <UNFILTERED>
    TEST_LIST = BOOL_OP,OR,COMPOSITE_TEST,<Unused>,TEST_CLAUSE,"TEST @Value(fme_type) = fme_area",area,"BOOL_OP,OR,COMPOSITE_TEST,""""""1"""""",TEST_CLAUSE,TEST @Value(fme_type) = fme_point",point
    area -> AttributeCreator_2
    point -> AttributeCreator_3
    <UNFILTERED> -> Aggregator_7
AttributeCreator_2
    ATTR_TABLE = SET_TO _name_extension = _search_bb
    -> StringConcatenator_7
StringConcatenator_7
    ACTION = Create New Attribute
    PARM_LINE = fme_basicstring:13%23%2:@Value(_name)@Value(_name_extension)_y
    VAL_ATTR = DatasetName
    -> TestFilter
AttributeCreator_3
    ATTR_TABLE = SET_TO _name_extension = _search
    -> StringConcatenator_8
StringConcatenator_8
    ACTION = Create New Attribute
    PARM_LINE = fme_basicstring:13%23%3:@Value(_name)@Value(_name_extension)_mp
    VAL_ATTR = DatasetName
    -> TestFilter
TestFilter
    DEFAULT_VALUE = <UNFILTERED>
    TEST_LIST = "BOOL_OP,OR,COMPOSITE_TEST,""""""1"""""",TEST_CLAUSE,TEST @Value(_name) = rk_ga",GA,"BOOL_OP,OR,COMPOSITE_TEST,""""""1"""""",TEST_CLAUSE,TEST @Value(_name) = rk_rattighet",RH
    GA -> AttributeKeeper_8
    RH -> AttributeKeeper_9
    <UNFILTERED> -> Aggregator_10
AttributeKeeper_8
    CREATE_BULK_MODE_FEATURES = NO
    KEEP_ATTRS = DatasetName,rk_fastighet
    -> fastighet_y01 (writer SDF3_1)
    -> GeometryFilter
    -> Table1 (writer POSTGIS_12)
    -> Table1 (writer POSTGIS_25)
GeometryFilter
    BREAK_AGG = No
    GEOM_PORT_NAMES = Point Area
    <UNFILTERED> -> Junction_21
    POINT -> Shapefile101 (writer SHAPEFILE_1)
    AREA -> Shapefile10101 (writer SHAPEFILE_1)
Note: Separeras på geometrityp för forcerande typ vid skrivande p.g.a. styrning till multipunkt. I annat fall om singel punkt är först förloras multipunkterna.
Shapefile101 (writer SHAPEFILE_1)
    attributes: rk_fastigh char(200)
Shapefile10101 (writer SHAPEFILE_1)
    attributes: rk_fastigh char(200)
fastighet_y01 (writer SDF3_1)
    attributes: rk_fastighet char(200)
Table1 (writer POSTGIS_25)
    attributes: rk_fastighet varchar(200)
Table1 (writer POSTGIS_12)
    attributes: rk_fastighet varchar(200)
AttributeKeeper_9
    CREATE_BULK_MODE_FEATURES = NO
    KEEP_ATTRS = DatasetName,rk_extid
    -> fastighet_y0100 (writer SDF3_1)
    -> GeometryFilter_2
    -> Table1 (writer POSTGIS_26)
    -> Table1 (writer POSTGIS_13)
GeometryFilter_2
    BREAK_AGG = No
    GEOM_PORT_NAMES = Point Area
    POINT -> Shapefile10100 (writer SHAPEFILE_1)
    AREA -> Shapefile1010000 (writer SHAPEFILE_1)
    <UNFILTERED> -> Junction_21
Note: Separeras på geometrityp för forcerande typ vid skrivande p.g.a. styrning till multipunkt. I annat fall om singel punkt är först förloras multipunkterna.
Shapefile10100 (writer SHAPEFILE_1)
    attributes: rk_extid char(200)
Shapefile1010000 (writer SHAPEFILE_1)
    attributes: rk_extid char(200)
Junction_21
    -> Aggregator_7
fastighet_y0100 (writer SDF3_1)
    attributes: rk_extid char(200)
Table1 (writer POSTGIS_26)
    attributes: rk_extid varchar(200)
Table1 (writer POSTGIS_13)
    attributes: rk_extid varchar(200)

Bookmark: Kontrollera om kolumnnamn förekommer fler än en gång per dataset
Tester_2
    BOOL_OP = AND
    TEST_CLAUSE:
      TEST @Value(dl_need_new_column_name) = true
      TEST @Value(dl_new_column_name) ATTRIBUTE_HAS_VALUE ""
    TEST_MODE = TEST
    PASSED -> AttributeCreator
AttributeCreator
    ATTR_TABLE = SET_TO column_name = @Value(dl_new_column_name)
    -> Aggregator_2
Aggregator_2
    ACCUM_ATTRS_NAME = Use Attributes From One Feature
    AGGREGATE_TYPE = Homogeneous Collection (If Possible)
    COUNT_ATTR = AntalSameColumns
    GROUP_BY = fme_feature_type_name dl_new_column_name
    MODE = Geometry - Assemble One Level
    ORDERED = No
    SEP = ,
    AGGREGATE -> Tester_3
Tester_3
    BOOL_OP = OR
    TEST_CLAUSE = TEST @Value(AntalSameColumns) > 1
    TEST_MODE = TEST
    PASSED -> Aggregator_4

FME custom transformer Bestammalese

Parameters:
- DATASET =
- FME_FEATURE_TYPE_NAME =
- FME_FORMAT_SHORT_NAME =
- _FILTERVALUE =

Input (input)
    -> FeatureReader [INITIATOR]
FeatureReader
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer
    <REJECTED> -> AttributeRenamer
AttributeExposer
    ATTR_LIST = td_id,rk_dep,rk_extid
    -> Tester
Tester
    BOOL_OP = OR
    TEST_CLAUSE = TEST rk_extid ATTRIBUTE_HAS_A_VALUE ""
    TEST_MODE = TEST
    PASSED -> FeatureMerger [SUPPLIER]
Input_2 (input)
    -> FeatureReader_2 [INITIATOR]
FeatureReader_2
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_2
    <REJECTED> -> AttributeRenamer
AttributeExposer_2
    ATTR_LIST = obj_id
    -> FeatureMerger [REQUESTOR]
FeatureMerger
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
Input_3 (input)
    -> FeatureReader_3 [INITIATOR]
FeatureReader_3
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_8
    <REJECTED> -> AttributeRenamer
AttributeExposer_8
    ATTR_LIST = td_id,rk_dep,rk_extid
    -> Tester_2
Tester_2
    BOOL_OP = OR
    TEST_CLAUSE = TEST rk_extid ATTRIBUTE_HAS_A_VALUE ""
    TEST_MODE = TEST
    PASSED -> FeatureMerger_2 [SUPPLIER]
Input_4 (input)
    -> FeatureReader_4 [INITIATOR]
FeatureReader_4
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_3
    <REJECTED> -> AttributeRenamer
AttributeExposer_3
    ATTR_LIST = obj_id
    -> FeatureMerger_2 [REQUESTOR]
FeatureMerger_2
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
Input_5 (input)
    -> FeatureReader_5 [INITIATOR]
FeatureReader_5
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_9
    <REJECTED> -> AttributeRenamer
AttributeExposer_9
    ATTR_LIST = td_id,rk_dep,rk_text
    -> Tester_3
Tester_3
    BOOL_OP = OR
    TEST_CLAUSE = TEST rk_text ATTRIBUTE_HAS_A_VALUE ""
    TEST_MODE = TEST
    PASSED -> FeatureMerger_3 [SUPPLIER]
Input_6 (input)
    -> FeatureReader_6 [INITIATOR]
FeatureReader_6
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_4
    <REJECTED> -> AttributeRenamer
AttributeExposer_4
    ATTR_LIST = obj_id
    -> FeatureMerger_3 [REQUESTOR]
FeatureMerger_3
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
Input_7 (input)
    -> FeatureReader_7 [INITIATOR]
FeatureReader_7
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_10
    <REJECTED> -> AttributeRenamer
AttributeExposer_10
    ATTR_LIST = td_id,rk_dep,rk_extid
    -> Tester_4
Tester_4
    BOOL_OP = OR
    TEST_CLAUSE = TEST rk_extid ATTRIBUTE_HAS_A_VALUE ""
    TEST_MODE = TEST
    PASSED -> FeatureMerger_4 [SUPPLIER]
Input_8 (input)
    -> FeatureReader_8 [INITIATOR]
FeatureReader_8
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_5
    <REJECTED> -> AttributeRenamer
AttributeExposer_5
    ATTR_LIST = obj_id
    -> FeatureMerger_4 [REQUESTOR]
FeatureMerger_4
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
Input_9 (input)
    -> FeatureReader_9 [INITIATOR]
FeatureReader_9
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_11
    <REJECTED> -> AttributeRenamer
AttributeExposer_11
    ATTR_LIST = td_id,rk_dep,rk_xyfel
    -> Tester_5
Tester_5
    BOOL_OP = OR
    TEST_CLAUSE = TEST rk_xyfel ATTRIBUTE_HAS_A_VALUE ""
    TEST_MODE = TEST
    PASSED -> FeatureMerger_5 [SUPPLIER]
Input_10 (input)
    -> FeatureReader_10 [INITIATOR]
FeatureReader_10
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_6
    <REJECTED> -> AttributeRenamer
AttributeExposer_6
    ATTR_LIST = obj_id
    -> FeatureMerger_5 [REQUESTOR]
FeatureMerger_5
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
Input_11 (input)
    -> FeatureReader_11 [INITIATOR]
FeatureReader_11
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_12
    <REJECTED> -> AttributeRenamer
AttributeExposer_12
    ATTR_LIST = td_id,rk_dep,rk_text
    -> Tester_7
Tester_7
    BOOL_OP = OR
    TEST_CLAUSE = TEST rk_text ATTRIBUTE_HAS_A_VALUE ""
    TEST_MODE = TEST
    PASSED -> FeatureMerger_6 [SUPPLIER]
Input_12 (input)
    -> FeatureReader_12 [INITIATOR]
FeatureReader_12
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_7
    <REJECTED> -> AttributeRenamer
AttributeExposer_7
    ATTR_LIST = obj_id
    -> FeatureMerger_6 [REQUESTOR]
FeatureMerger_6
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
Output (output)
AttributeRenamer
    ATTR_TABLE:
      RENAME_SET_DEFAULT _reader_error > error_msg
      RENAME_SET_DEFAULT fme_rejection_code > error_msg
    -> <Rejected> (output)
<Rejected> (output)

FME custom transformer Rättigheter

Parameters:
- DATASET =
- FME_FEATURE_TYPE_NAME =
- FME_FORMAT_SHORT_NAME =
- _FILTERVALUE =

FeatureReader
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_8
    <REJECTED> -> AttributeRenamer
AttributeExposer_8
    ATTR_LIST = td_id,rk_dep,rk_extid,rk_xyfel
    -> Tester
    -> Huvudobjekt (output)
Tester
    BOOL_OP = OR
    TEST_CLAUSE = TEST rk_extid ATTRIBUTE_HAS_A_VALUE ""
    TEST_MODE = TEST
    PASSED -> FeatureMerger [SUPPLIER]
FeatureReader_2
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_9
    <REJECTED> -> AttributeRenamer
AttributeExposer_9
    ATTR_LIST = obj_id
    -> FeatureMerger [REQUESTOR]
FeatureMerger
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_3
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_10
    <REJECTED> -> AttributeRenamer
AttributeExposer_10
    ATTR_LIST = td_id,rk_dep,rk_extid,rk_xyfel
    -> Tester_2
    -> Huvudobjekt (output)
Tester_2
    BOOL_OP = OR
    TEST_CLAUSE = TEST rk_extid ATTRIBUTE_HAS_A_VALUE ""
    TEST_MODE = TEST
    PASSED -> FeatureMerger_2 [SUPPLIER]
FeatureReader_4
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_2
    <REJECTED> -> AttributeRenamer
AttributeExposer_2
    ATTR_LIST = obj_id
    -> FeatureMerger_2 [REQUESTOR]
FeatureMerger_2
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_5
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_11
    <REJECTED> -> AttributeRenamer
AttributeExposer_11
    ATTR_LIST = td_id,rk_dep,rk_extid,rk_xyfel
    -> Tester_3
    -> Huvudobjekt (output)
Tester_3
    BOOL_OP = OR
    TEST_CLAUSE = TEST rk_extid ATTRIBUTE_HAS_A_VALUE ""
    TEST_MODE = TEST
    PASSED -> FeatureMerger_3 [SUPPLIER]
Huvudobjekt (output)
FeatureReader_6
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_3
    <REJECTED> -> AttributeRenamer
AttributeExposer_3
    ATTR_LIST = obj_id
    -> FeatureMerger_3 [REQUESTOR]
FeatureMerger_3
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_7
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_12
    <REJECTED> -> AttributeRenamer
AttributeExposer_12
    ATTR_LIST = td_id,rk_dep,rk_extid
    -> Tester_4
Tester_4
    BOOL_OP = OR
    TEST_CLAUSE = TEST rk_extid ATTRIBUTE_HAS_A_VALUE ""
    TEST_MODE = TEST
    PASSED -> FeatureMerger_4 [SUPPLIER]
FeatureReader_8
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_4
    <REJECTED> -> AttributeRenamer
AttributeExposer_4
    ATTR_LIST = obj_id
    -> FeatureMerger_4 [REQUESTOR]
FeatureMerger_4
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_9
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_13
    <REJECTED> -> AttributeRenamer
AttributeExposer_13
    ATTR_LIST = td_id,rk_dep,rk_text,rk_trakt,rk_block_enhet
    -> Tester_5
Tester_5
    BOOL_OP = OR
    TEST_CLAUSE = TEST rk_text ATTRIBUTE_HAS_A_VALUE ""
    TEST_MODE = TEST
    PASSED -> FeatureMerger_5 [SUPPLIER]
FeatureReader_10
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_5
    <REJECTED> -> AttributeRenamer
AttributeExposer_5
    ATTR_LIST = obj_id
    -> FeatureMerger_5 [REQUESTOR]
FeatureMerger_5
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_11
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_14
    <REJECTED> -> AttributeRenamer
AttributeExposer_14
    ATTR_LIST = td_id,rk_dep,rk_xyfel
    -> Tester_6
Tester_6
    BOOL_OP = OR
    TEST_CLAUSE = TEST rk_xyfel ATTRIBUTE_HAS_A_VALUE ""
    TEST_MODE = TEST
    PASSED -> FeatureMerger_6 [SUPPLIER]
FeatureReader_12
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_6
    <REJECTED> -> AttributeRenamer
AttributeExposer_6
    ATTR_LIST = obj_id
    -> FeatureMerger_6 [REQUESTOR]
FeatureMerger_6
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_13
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_15
    <REJECTED> -> AttributeRenamer
AttributeExposer_15
    ATTR_LIST = td_id,rk_dep,rk_text
    -> Tester_7
Tester_7
    BOOL_OP = OR
    TEST_CLAUSE = TEST rk_text ATTRIBUTE_HAS_A_VALUE ""
    TEST_MODE = TEST
    PASSED -> FeatureMerger_7 [SUPPLIER]
FeatureReader_14
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_7
    <REJECTED> -> AttributeRenamer
AttributeExposer_7
    ATTR_LIST = obj_id
    -> FeatureMerger_7 [REQUESTOR]
FeatureMerger_7
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
Output (output)
AttributeRenamer
    ATTR_TABLE:
      RENAME_SET_DEFAULT _reader_error > error_msg
      RENAME_SET_DEFAULT fme_rejection_code > error_msg
    -> <Rejected> (output)
<Rejected> (output)

Bookmark: rk_rattighet_l
Input (input)
    -> FeatureReader [INITIATOR]
Input_2 (input)
    -> FeatureReader_2 [INITIATOR]

Bookmark: rk_rattighet_p
Input_3 (input)
    -> FeatureReader_3 [INITIATOR]
Input_4 (input)
    -> FeatureReader_4 [INITIATOR]

Bookmark: rk_rattighet_y
Input_5 (input)
    -> FeatureReader_5 [INITIATOR]
Input_6 (input)
    -> FeatureReader_6 [INITIATOR]

Bookmark: rk_rattighetid_p
Input_7 (input)
    -> FeatureReader_7 [INITIATOR]
Input_8 (input)
    -> FeatureReader_8 [INITIATOR]

Bookmark: rk_rattighetidtext_p
Input_9 (input)
    -> FeatureReader_9 [INITIATOR]
Input_10 (input)
    -> FeatureReader_10 [INITIATOR]

Bookmark: rk_rattighetomrade_l
Input_11 (input)
    -> FeatureReader_11 [INITIATOR]
Input_12 (input)
    -> FeatureReader_12 [INITIATOR]

Bookmark: rk_rattighettext_p
Input_13 (input)
    -> FeatureReader_13 [INITIATOR]
Input_14 (input)
    -> FeatureReader_14 [INITIATOR]

FME custom transformer 3D

Parameters:
- DATASET =
- FME_FEATURE_TYPE_NAME =
- FME_FORMAT_SHORT_NAME =
- OutSchemaFileNameSuffix =
- ProcessModulName =
- RotDirectory =
- _FILTERVALUE =

Input (input)
    -> FeatureReader [INITIATOR]
FeatureReader
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer
    <REJECTED> -> AttributeRenamer
AttributeExposer
    ATTR_LIST = td_id,rk_dep,rk_trakt,rk_block_enhet,rk_omrade,rk_tillagg,rk_fastighet
    -> Tester
Tester
    BOOL_OP = OR
    TEST_CLAUSE = TEST rk_fastighet ATTRIBUTE_HAS_A_VALUE ""
    TEST_MODE = TEST
    PASSED -> FeatureMerger [SUPPLIER]
Input_2 (input)
    -> FeatureReader_2 [INITIATOR]
FeatureReader_2
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_9
    <REJECTED> -> AttributeRenamer
AttributeExposer_9
    ATTR_LIST = obj_id
    -> FeatureMerger [REQUESTOR]
FeatureMerger
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
Input_3 (input)
    -> FeatureReader_3 [INITIATOR]
FeatureReader_3
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_5
    <REJECTED> -> AttributeRenamer
AttributeExposer_5
    ATTR_LIST = td_id,rk_dep,rk_trakt,rk_block_enhet,rk_omrade,rk_tillagg,rk_fastighet
    -> Tester_5
Tester_5
    BOOL_OP = OR
    TEST_CLAUSE = TEST rk_fastighet ATTRIBUTE_HAS_A_VALUE ""
    TEST_MODE = TEST
    PASSED -> FeatureMerger_2 [SUPPLIER]
Input_4 (input)
    -> FeatureReader_4 [INITIATOR]
FeatureReader_4
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_2
    <REJECTED> -> AttributeRenamer
AttributeExposer_2
    ATTR_LIST = obj_id
    -> FeatureMerger_2 [REQUESTOR]
FeatureMerger_2
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
Input_5 (input)
    -> FeatureReader_5 [INITIATOR]
FeatureReader_5
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_6
    <REJECTED> -> AttributeRenamer
AttributeExposer_6
    ATTR_LIST = td_id,rk_dep,rk_trakt,rk_block_enhet,rk_omrade,rk_tillagg
    -> Tester_2
Tester_2
    BOOL_OP = OR
    TEST_CLAUSE = TEST rk_block_enhet ATTRIBUTE_HAS_A_VALUE ""
    TEST_MODE = TEST
    PASSED -> FeatureMerger_3 [SUPPLIER]
Input_6 (input)
    -> FeatureReader_6 [INITIATOR]
FeatureReader_6
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_3
    <REJECTED> -> AttributeRenamer
AttributeExposer_3
    ATTR_LIST = obj_id
    -> FeatureMerger_3 [REQUESTOR]
FeatureMerger_3
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
Input_7 (input)
    -> FeatureReader_7 [INITIATOR]
FeatureReader_7
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_7
    <REJECTED> -> AttributeRenamer
AttributeExposer_7
    ATTR_LIST = td_id,rk_dep,rk_xyfel
    -> Tester_4
Tester_4
    BOOL_OP = OR
    TEST_CLAUSE = TEST rk_xyfel ATTRIBUTE_HAS_A_VALUE ""
    TEST_MODE = TEST
    PASSED -> FeatureMerger_4 [SUPPLIER]
Input_8 (input)
    -> FeatureReader_8 [INITIATOR]
FeatureReader_8
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_4
    <REJECTED> -> AttributeRenamer
AttributeExposer_4
    ATTR_LIST = obj_id
    -> FeatureMerger_4 [REQUESTOR]
FeatureMerger_4
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
Output (output)
AttributeRenamer
    ATTR_TABLE:
      RENAME_SET_DEFAULT _reader_error > error_msg
      RENAME_SET_DEFAULT fme_rejection_code > error_msg
    -> <Rejected> (output)
<Rejected> (output)

FME custom transformer GA

Parameters:
- DATASET =
- FME_FEATURE_TYPE_NAME =
- FME_FORMAT_SHORT_NAME =
- _FILTERVALUE =

FeatureReader
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer
    <REJECTED> -> AttributeRenamer
AttributeExposer
    ATTR_LIST = td_id,rk_dep,rk_trakt,rk_block_enhet,rk_fastighet
    -> Tester
    -> Huvudobjekt (output)
Tester
    BOOL_OP = OR
    TEST_CLAUSE = TEST rk_fastighet ATTRIBUTE_HAS_A_VALUE ""
    TEST_MODE = TEST
    PASSED -> FeatureMerger [SUPPLIER]
FeatureReader_2
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_9
    <REJECTED> -> AttributeRenamer
AttributeExposer_9
    ATTR_LIST = obj_id
    -> FeatureMerger [REQUESTOR]
FeatureMerger
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_3
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_6
    <REJECTED> -> AttributeRenamer
AttributeExposer_6
    ATTR_LIST = td_id,rk_dep,rk_trakt,rk_block_enhet,rk_fastighet
    -> Tester_2
    -> Huvudobjekt (output)
Tester_2
    BOOL_OP = OR
    TEST_CLAUSE = TEST rk_fastighet ATTRIBUTE_HAS_A_VALUE ""
    TEST_MODE = TEST
    PASSED -> FeatureMerger_2 [SUPPLIER]
FeatureReader_4
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_2
    <REJECTED> -> AttributeRenamer
AttributeExposer_2
    ATTR_LIST = obj_id
    -> FeatureMerger_2 [REQUESTOR]
FeatureMerger_2
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_5
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_7
    <REJECTED> -> AttributeRenamer
AttributeExposer_7
    ATTR_LIST = td_id,rk_dep,rk_trakt,rk_block_enhet,rk_fastighet
    -> Tester_3
    -> Huvudobjekt (output)
Huvudobjekt (output)
Tester_3
    BOOL_OP = OR
    TEST_CLAUSE = TEST rk_fastighet ATTRIBUTE_HAS_A_VALUE ""
    TEST_MODE = TEST
    PASSED -> FeatureMerger_3 [SUPPLIER]
FeatureReader_6
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_3
    <REJECTED> -> AttributeRenamer
AttributeExposer_3
    ATTR_LIST = obj_id
    -> FeatureMerger_3 [REQUESTOR]
FeatureMerger_3
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_7
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_8
    <REJECTED> -> AttributeRenamer
AttributeExposer_8
    ATTR_LIST = td_id,rk_dep,rk_xyfel
    -> Tester_4
Tester_4
    BOOL_OP = OR
    TEST_CLAUSE = TEST rk_xyfel ATTRIBUTE_HAS_A_VALUE ""
    TEST_MODE = TEST
    PASSED -> FeatureMerger_4 [SUPPLIER]
FeatureReader_8
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_4
    <REJECTED> -> AttributeRenamer
AttributeExposer_4
    ATTR_LIST = obj_id
    -> FeatureMerger_4 [REQUESTOR]
FeatureMerger_4
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_9
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_10
    <REJECTED> -> AttributeRenamer
AttributeExposer_10
    ATTR_LIST = td_id,rk_dep,rk_text
    -> Tester_5
Tester_5
    BOOL_OP = OR
    TEST_CLAUSE = TEST rk_text ATTRIBUTE_HAS_A_VALUE ""
    TEST_MODE = TEST
    PASSED -> FeatureMerger_5 [SUPPLIER]
FeatureReader_10
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_5
    <REJECTED> -> AttributeRenamer
AttributeExposer_5
    ATTR_LIST = obj_id
    -> FeatureMerger_5 [REQUESTOR]
FeatureMerger_5
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
Output (output)
AttributeRenamer
    ATTR_TABLE:
      RENAME_SET_DEFAULT _reader_error > error_msg
      RENAME_SET_DEFAULT fme_rejection_code > error_msg
    -> <Rejected> (output)
<Rejected> (output)

Bookmark: rk_ga_l
Input (input)
    -> FeatureReader [INITIATOR]
Input_2 (input)
    -> FeatureReader_2 [INITIATOR]

Bookmark: rk_ga_p
Input_3 (input)
    -> FeatureReader_3 [INITIATOR]
Input_4 (input)
    -> FeatureReader_4 [INITIATOR]

Bookmark: rk_ga_y
Input_5 (input)
    -> FeatureReader_5 [INITIATOR]
Input_6 (input)
    -> FeatureReader_6 [INITIATOR]

Bookmark: rk_gaomrade_l
Input_7 (input)
    -> FeatureReader_7 [INITIATOR]
Input_8 (input)
    -> FeatureReader_8 [INITIATOR]

Bookmark: rk_gatext_p
Input_9 (input)
    -> FeatureReader_9 [INITIATOR]
Input_10 (input)
    -> FeatureReader_10 [INITIATOR]

FME custom transformer SearchBoundingBoxAndPoint

Parameters:
- ATTRIBUTES =
- ProcessModulName =
- RotDirectory =

Input (input)
    -> AttributeExposer_2
AttributeExposer_2
    ATTR_LIST = fme_type
    -> TestFilter_5
Note: yta linje eller punkt
TestFilter_5
    DEFAULT_VALUE = <UNFILTERED>
    TEST_LIST = BOOL_OP,OR,COMPOSITE_TEST,<Unused>,TEST_CLAUSE,"TEST @Value(fme_type) = fme_area",area,BOOL_OP,OR,COMPOSITE_TEST,<Unused>,TEST_CLAUSE,"TEST @Value(fme_type) = fme_line",line,"BOOL_OP,OR,COMPOSITE_TEST,""""""1"""""",TEST_CLAUSE,TEST @Value(fme_type) = fme_point",point
    area -> CenterPointReplacer
    area -> Aggregator_4
    line -> Snipper
    line -> Aggregator_4
    point -> Bufferer
    point -> Junction_5
    <UNFILTERED> -> StringConcatenator
BoundingBox (output)
point (output)
<Rejected> (output)

Bookmark: Sökunderlag yta
Bufferer
    ANGLE = 22.5
    CAP_STYLE = Arc
    CORNER_STYLE = Arc
    MODE = AREA
    OFFSET = 1
    OFFSET_UNITS = NONE
    PRECISION = APPROX
    BUFFERED -> Aggregator_4
    <REJECTED> -> Aggregator
Aggregator_4
    ACCUM_ATTRS_NAME = Use Attributes From One Feature
    AGGREGATE_TYPE = Homogeneous Collection (If Possible)
    GROUP_BY = $(ATTRIBUTES)
    MODE = Geometry - Assemble One Level
    SEP = ,
    AGGREGATE -> BoundingBoxReplacer
BoundingBoxReplacer
    BOXTYPE = 2D Bounding Box
    BOX -> BoundingBox (output)

Bookmark: Sökunderlag punkt
Note: Sökpunkt representation yta
CenterPointReplacer
    POINTTYPE = INSIDE
    POINT -> Junction_5
    UNTOUCHED -> Aggregator
Note: Sökpunkt representation linje
Snipper
    DEAGGREGATE_INPUT = YES
    ENDLOCATIONATTR = 50
    MEASUREMENTTYPE = 2D
    SNIPMODE = Distance (Percentage)
    STARTLOCATIONATTR = 50
    -> Junction_5
    <REJECTED> -> Aggregator
Junction_5
    -> Aggregator_5
Aggregator_5
    ACCUM_ATTRS_NAME = Use Attributes From One Feature
    AGGREGATE_TYPE = Homogeneous Collection (If Possible)
    GROUP_BY = $(ATTRIBUTES)
    MODE = Geometry - Assemble One Level
    SEP = ,
    AGGREGATE -> point (output)

Bookmark: Felmeddelande homogeniserad till en post
Aggregator
    ACCUM_ATTRS_NAME = Use Attributes From One Feature
    AGGREGATE_TYPE = Homogeneous Collection (If Possible)
    GROUP_BY = fme_rejection_code
    MODE = Geometry - Assemble One Level
    SEP = ,
    AGGREGATE -> AttributeRenamer
AttributeRenamer
    ATTR_TABLE = RENAME_SET_DEFAULT fme_rejection_code > error_msg
    MISSING_INPUT_ATTRS = REMOVE
    -> Aggregator_3
StringConcatenator
    ACTION = Create New Attribute
    PARM_LINE = fme_basicstring:19%16%55:Följande fme_type '@Value(fme_type)' hanterades inte men förekom. Ställningstagande krävs.
    VAL_ATTR = error_msg
    -> Aggregator_2
Aggregator_2
    ACCUM_ATTRS_NAME = Use Attributes From One Feature
    AGGREGATE_TYPE = Homogeneous Collection (If Possible)
    GROUP_BY = error_msg
    MODE = Geometry - Assemble One Level
    SEP = ,
    AGGREGATE -> Aggregator_3
Aggregator_3
    ACCUM_ATTRS_NAME = Use Attributes From One Feature
    AGGREGATE_TYPE = Homogeneous Collection (If Possible)
    GROUP_BY = error_msg
    MODE = Geometry - Assemble One Level
    SEP = ,
    AGGREGATE -> ListBuilder
ListBuilder
    LIST_ATTRS_TO_INCLUDE = error_msg
    LIST_NAME = _error_msgs
    -> ListConcatenator
ListConcatenator
    DROP_EMPTY_PARTS = Yes
    LIST_ATTR = _error_msgs{}.error_msg
    SEP = "\n"
    VAL_ATTR = error_msg
    -> <Rejected> (output)

FME custom transformer Plan

Parameters:
- DATASET =
- FME_FEATURE_TYPE_NAME =
- FME_FORMAT_SHORT_NAME =
- _FILTERVALUE =

FeatureReader
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_10
    <REJECTED> -> AttributeRenamer
AttributeExposer_10
    ATTR_LIST = td_id,rk_dep,rk_extid
    -> Tester
Tester
    BOOL_OP = OR
    COMPOSITE_TEST = 1
    TEST_CLAUSE = TEST rk_extid ATTRIBUTE_HAS_A_VALUE ""
    TEST_MODE = TEST
    PASSED -> FeatureMerger [SUPPLIER]
FeatureReader_2
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_2
    <REJECTED> -> AttributeRenamer
AttributeExposer_2
    ATTR_LIST = obj_id
    -> FeatureMerger [REQUESTOR]
FeatureMerger
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_3
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_7
    <REJECTED> -> AttributeRenamer
AttributeExposer_7
    ATTR_LIST = td_id,rk_dep,rk_text
    -> Tester_2
Tester_2
    BOOL_OP = OR
    COMPOSITE_TEST = 1
    TEST_CLAUSE = TEST rk_text ATTRIBUTE_HAS_A_VALUE ""
    TEST_MODE = TEST
    PASSED -> FeatureMerger_2 [SUPPLIER]
FeatureReader_4
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_3
    <REJECTED> -> AttributeRenamer
AttributeExposer_3
    ATTR_LIST = obj_id
    -> FeatureMerger_2 [REQUESTOR]
FeatureMerger_2
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_5
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_8
    <REJECTED> -> AttributeRenamer
AttributeExposer_8
    ATTR_LIST = td_id,rk_dep,rk_extid
    -> Tester_3
Tester_3
    BOOL_OP = OR
    COMPOSITE_TEST = 1
    TEST_CLAUSE = TEST rk_extid ATTRIBUTE_HAS_A_VALUE ""
    TEST_MODE = TEST
    PASSED -> FeatureMerger_3 [SUPPLIER]
FeatureReader_6
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_4
    <REJECTED> -> AttributeRenamer
AttributeExposer_4
    ATTR_LIST = obj_id
    -> FeatureMerger_3 [REQUESTOR]
FeatureMerger_3
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_7
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_9
    <REJECTED> -> AttributeRenamer
AttributeExposer_9
    ATTR_LIST = td_id,rk_dep,rk_text
    -> Tester_4
Tester_4
    BOOL_OP = OR
    COMPOSITE_TEST = 1
    TEST_CLAUSE = TEST rk_text ATTRIBUTE_HAS_A_VALUE ""
    TEST_MODE = TEST
    PASSED -> FeatureMerger_4 [SUPPLIER]
FeatureReader_8
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_5
    <REJECTED> -> AttributeRenamer
AttributeExposer_5
    ATTR_LIST = obj_id
    -> FeatureMerger_4 [REQUESTOR]
FeatureMerger_4
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_9
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_11
    <REJECTED> -> AttributeRenamer
AttributeExposer_11
    ATTR_LIST = td_id,rk_dep,rk_xyfel
    -> Tester_5
Tester_5
    BOOL_OP = OR
    COMPOSITE_TEST = 1
    TEST_CLAUSE = TEST rk_xyfel ATTRIBUTE_HAS_A_VALUE ""
    TEST_MODE = TEST
    PASSED -> FeatureMerger_5 [SUPPLIER]
FeatureReader_10
    ATTR_ACCUM_MODE = Only Use Result
    COMBINE_GEOM = Use Result
    DATASET = @Value(Dataset)
    FEATURETYPES = @Value(fme_feature_type_name)
    FORMAT = POSTGIS
    INTERACT = NONE
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_6
    <REJECTED> -> AttributeRenamer
AttributeExposer_6
    ATTR_LIST = obj_id
    -> FeatureMerger_5 [REQUESTOR]
FeatureMerger_5
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
Output (output)
AttributeRenamer
    ATTR_TABLE:
      RENAME_SET_DEFAULT _reader_error > error_msg
      RENAME_SET_DEFAULT fme_rejection_code > error_msg
    MISSING_INPUT_ATTRS = PRESERVE
    -> <Rejected> (output)
<Rejected> (output)

Bookmark: rk_plan_y
Input (input)
    -> FeatureReader [INITIATOR]
Input_2 (input)
    -> FeatureReader_2 [INITIATOR]

Bookmark: rk_planadmtext_p
Input_3 (input)
    -> FeatureReader_3 [INITIATOR]
Input_4 (input)
    -> FeatureReader_4 [INITIATOR]

Bookmark: rk_planid_p
Input_5 (input)
    -> FeatureReader_5 [INITIATOR]
Input_6 (input)
    -> FeatureReader_6 [INITIATOR]

Bookmark: rk_planidtext_p
Input_7 (input)
    -> FeatureReader_7 [INITIATOR]
Input_8 (input)
    -> FeatureReader_8 [INITIATOR]

Bookmark: rk_planomrade_l
Input_9 (input)
    -> FeatureReader_9 [INITIATOR]
Input_10 (input)
    -> FeatureReader_10 [INITIATOR]

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    INCLUDE_OFFSET = NO
    STAMP_TYPE = datetime
    TIMEZONE = local
    -> DateTimeConverter
DateTimeConverter
    DATETIME_ATTR = _dts
    OUT_FORMAT = %Y-%m-%d %H:%M:%S
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    NO_MATCH = _FME_NO_OP_
    REGEXP = YES
    SRC_ATTRS = _dts
    -> StringReplacer_2
StringReplacer_2
    CASE = NO
    FIND_TEXT = .*\.
    NO_MATCH = _FME_NO_OP_
    REGEXP = YES
    SRC_ATTRS = _mils
    -> SubstringExtractor
SubstringExtractor
    END = 2
    RESULT_ATTR = _subMils
    SRC_STRING = @Value(_mils)
    START = 0
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)

FME custom transformer vektor2vinklar

Input (input)
    -> CoordinateExtractor
ExpressionEvaluator_22
    ACTION = Create New Attribute
    EXPRESSION = @Value(radianer)*180/@pi()
    VAL_ATTR = grader
    -> TestFilter_5
Note: Sätter ingen vridning
AttributeCreator_6
    ATTR_TABLE:
      SET_TO radianer = 0
      SET_TO grader = 0
      SET_TO gon = 100
    -> Junction_4
VertexCreator_7
    MODE_NAME = Replace with Point
    XVAL = @Value(x1)
    YVAL = @Value(y1)
    -> AttributeRemover
AttributeRemover
    LIST_ATTRS = _indices{}
    REMOVE_ATTRS = y2,y1,diffY,z2,radianer2gon,diffX,x1,radianer2grader,x2,z1
    -> Output (output)
Output (output)

Bookmark: Koordinatdiffar i x- och y-led
CoordinateExtractor
    LIST_NAME = _indices
    MODE = All Coordinates
    -> AttributeCreator
AttributeCreator
    ATTR_TABLE:
      SET_TO x1 = @Value(_indices{0}.x)
      SET_TO y1 = @Value(_indices{0}.y)
      SET_TO z1 = @Value(_indices{0}.z)
      SET_TO x2 = @Value(_indices{1}.x)
      SET_TO y2 = @Value(_indices{1}.y)
      SET_TO z2 = @Value(_indices{1}.z)
    -> AttributeCreator_5
AttributeCreator_5
    ATTR_TABLE:
      SET_TO diffX = @Evaluate(@Value(x2)-@Value(x1))
      SET_TO diffY = @Evaluate(@Value(y2)-@Value(y1))
    -> ExpressionEvaluator_16

Bookmark: Radianer höger- och vänstervridet
ExpressionEvaluator_16
    ACTION = Create New Attribute
    EXPRESSION = @atan2(@Value(diffY),@Value(diffX))
    VAL_ATTR = radianer2grader
    -> ExpressionEvaluator_17
ExpressionEvaluator_17
    ACTION = Create New Attribute
    EXPRESSION = @atan2(@Value(diffX),@Value(diffY))
    VAL_ATTR = radianer2gon
    -> TestFilter_4

Bookmark: Teckenhantering radianer/grader
TestFilter_4
    DEFAULT_VALUE = <UNFILTERED>
    TEST_LIST:
      "BOOL_OP,AND,COMPOSITE_TEST,""""""<Unused>"""""",TEST_CLAUSE,TEST @Value(diffX) > 0
      TEST @Value(diffY) > 0",Kvadrant 1,"BOOL_OP,AND,COMPOSITE_TEST,""""""<Unused>"""""",TEST_CLAUSE,TEST @Value(diffX) < 0
      TEST @Value(diffY) > 0",Kvadrant 2,"BOOL_OP,AND,COMPOSITE_TEST,""""""<Unused>"""""",TEST_CLAUSE,TEST @Value(diffX) < 0
      TEST @Value(diffY) < 0",Kvadrant 3,"BOOL_OP,AND,COMPOSITE_TEST,""""""<Unused>"""""",TEST_CLAUSE,TEST @Value(diffX) > 0
      TEST @Value(diffY) < 0",Kvadrant 4
    Kvadrant 1 -> AttributeCopier_3
    Kvadrant 2 -> AttributeCopier_3
    Kvadrant 3 -> ExpressionEvaluator_18
    Kvadrant 4 -> ExpressionEvaluator_18
    <UNFILTERED> -> AttributeCreator_6
AttributeCopier_3
    ATTR_TABLE = COPY radianer2grader > radianer
    -> Junction_3
ExpressionEvaluator_18
    ACTION = Create New Attribute
    EXPRESSION = @Value(radianer2grader)+2*@pi()
    VAL_ATTR = radianer
    -> Junction_3
Junction_3
    -> ExpressionEvaluator_22

Bookmark: Teckenhantering gon (nygrader)
TestFilter_5
    DEFAULT_VALUE = <UNFILTERED>
    TEST_LIST:
      "BOOL_OP,AND,COMPOSITE_TEST,""""""<Unused>"""""",TEST_CLAUSE,TEST @Value(diffY) > 0
      TEST @Value(diffX) > 0",Kvadrant 1,"BOOL_OP,AND,COMPOSITE_TEST,""""""<Unused>"""""",TEST_CLAUSE,TEST @Value(diffY) < 0
      TEST @Value(diffX) > 0",Kvadrant 2,"BOOL_OP,AND,COMPOSITE_TEST,""""""<Unused>"""""",TEST_CLAUSE,TEST @Value(diffY) < 0
      TEST @Value(diffX) < 0",Kvadrant 3,"BOOL_OP,AND,COMPOSITE_TEST,""""""<Unused>"""""",TEST_CLAUSE,TEST @Value(diffY) > 0
      TEST @Value(diffX) < 0",Kvadrant 4
    Kvadrant 1 -> ExpressionEvaluator_19
    Kvadrant 2 -> ExpressionEvaluator_19
    Kvadrant 3 -> ExpressionEvaluator_20
    Kvadrant 4 -> ExpressionEvaluator_21
ExpressionEvaluator_19
    ACTION = Create New Attribute
    EXPRESSION = @Value(radianer2gon)*200/@pi()
    VAL_ATTR = gon
    -> Junction_4
ExpressionEvaluator_20
    ACTION = Create New Attribute
    EXPRESSION = @Value(radianer2gon)*200/@pi()+400
    VAL_ATTR = gon
    -> Junction_4
ExpressionEvaluator_21
    ACTION = Create New Attribute
    EXPRESSION = @Value(radianer2gon)*200/@pi()+400
    VAL_ATTR = gon
    -> Junction_4
Junction_4
    -> VertexCreator_7

FME custom transformer Fastighet

Parameters:
- DATASET =
- FME_FEATURE_TYPE_NAME =
- FME_FORMAT_SHORT_NAME =
- _FILTERVALUE =

FeatureReader
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer
    <REJECTED> -> AttributeRenamer
AttributeExposer
    ATTR_LIST = td_id,rk_dep,rk_trakt,rk_block_enhet,rk_omrade,rk_tillagg,rk_fastighet
    -> Tester
Tester
    BOOL_OP = OR
    TEST_CLAUSE = TEST rk_fastighet ATTRIBUTE_HAS_A_VALUE ""
    TEST_MODE = TEST
    PASSED -> FeatureMerger [SUPPLIER]
FeatureReader_2
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_2
    <REJECTED> -> AttributeRenamer
AttributeExposer_2
    ATTR_LIST = obj_id
    -> FeatureMerger [REQUESTOR]
FeatureMerger
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_3
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_11
    <REJECTED> -> AttributeRenamer
AttributeExposer_11
    ATTR_LIST = td_id,rk_dep,rk_trakt,rk_block_enhet,rk_omrade,rk_tillagg,rk_fastighet
    -> Tester_2
Tester_2
    BOOL_OP = OR
    TEST_CLAUSE = TEST rk_fastighet ATTRIBUTE_HAS_A_VALUE ""
    TEST_MODE = TEST
    PASSED -> FeatureMerger_2 [SUPPLIER]
FeatureReader_4
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_3
    <REJECTED> -> AttributeRenamer
AttributeExposer_3
    ATTR_LIST = obj_id
    -> FeatureMerger_2 [REQUESTOR]
FeatureMerger_2
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_5
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_12
    <REJECTED> -> AttributeRenamer
AttributeExposer_12
    ATTR_LIST = td_id,rk_dep,rk_trakt,rk_block_enhet,rk_omrade,rk_tillagg,rk_fastighet
    -> Tester_8
Tester_8
    BOOL_OP = OR
    TEST_CLAUSE = TEST rk_fastighet ATTRIBUTE_HAS_A_VALUE ""
    TEST_MODE = TEST
    PASSED -> FeatureMerger_8 [SUPPLIER]
FeatureReader_6
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_4
    <REJECTED> -> AttributeRenamer
AttributeExposer_4
    ATTR_LIST = obj_id
    -> FeatureMerger_8 [REQUESTOR]
FeatureMerger_8
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_7
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_13
    <REJECTED> -> AttributeRenamer
AttributeExposer_13
    ATTR_LIST = td_id,rk_dep,rk_text
    -> Tester_3
Tester_3
    BOOL_OP = OR
    TEST_CLAUSE = TEST rk_text ATTRIBUTE_HAS_A_VALUE ""
    TEST_MODE = TEST
    PASSED -> FeatureMerger_3 [SUPPLIER]
FeatureReader_8
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_5
    <REJECTED> -> AttributeRenamer
AttributeExposer_5
    ATTR_LIST = obj_id
    -> FeatureMerger_3 [REQUESTOR]
FeatureMerger_3
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_9
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_14
    <REJECTED> -> AttributeRenamer
AttributeExposer_14
    ATTR_LIST = td_id,rk_dep,rk_xyfel
    -> Tester_4
Tester_4
    BOOL_OP = OR
    TEST_CLAUSE = TEST rk_xyfel ATTRIBUTE_HAS_A_VALUE ""
    TEST_MODE = TEST
    PASSED -> FeatureMerger_4 [SUPPLIER]
FeatureReader_10
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_6
    <REJECTED> -> AttributeRenamer
AttributeExposer_6
    ATTR_LIST = obj_id
    -> FeatureMerger_4 [REQUESTOR]
FeatureMerger_4
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_11
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_15
    <REJECTED> -> AttributeRenamer
AttributeExposer_15
    ATTR_LIST = td_id,rk_dep,rk_trakt,rk_block_enhet,rk_omrade,rk_fastighet
    -> Tester_5
Tester_5
    BOOL_OP = OR
    TEST_CLAUSE = TEST rk_fastighet ATTRIBUTE_HAS_A_VALUE ""
    TEST_MODE = TEST
    PASSED -> FeatureMerger_5 [SUPPLIER]
FeatureReader_12
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_7
    <REJECTED> -> AttributeRenamer
AttributeExposer_7
    ATTR_LIST = obj_id
    -> FeatureMerger_5 [REQUESTOR]
FeatureMerger_5
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_13
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_16
    <REJECTED> -> AttributeRenamer
AttributeExposer_16
    ATTR_LIST = td_id,rk_dep,rk_trakt,rk_block_enhet,rk_omrade,rk_tillagg
    -> Tester_6
Tester_6
    BOOL_OP = OR
    TEST_CLAUSE = TEST rk_block_enhet ATTRIBUTE_HAS_A_VALUE ""
    TEST_MODE = TEST
    PASSED -> FeatureMerger_6 [SUPPLIER]
FeatureReader_14
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_8
    <REJECTED> -> AttributeRenamer
AttributeExposer_8
    ATTR_LIST = obj_id
    -> FeatureMerger_6 [REQUESTOR]
FeatureMerger_6
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_15
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_17
    <REJECTED> -> AttributeRenamer
AttributeExposer_17
    ATTR_LIST = td_id,rk_dep,rk_trakt,rk_block_enhet,rk_omrade,rk_tillagg
    -> Tester_7
Tester_7
    BOOL_OP = OR
    TEST_CLAUSE = TEST rk_block_enhet ATTRIBUTE_HAS_A_VALUE ""
    TEST_MODE = TEST
    PASSED -> FeatureMerger_7 [SUPPLIER]
FeatureReader_16
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_9
    <REJECTED> -> AttributeRenamer
AttributeExposer_9
    ATTR_LIST = obj_id
    -> FeatureMerger_7 [REQUESTOR]
FeatureMerger_7
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
FeatureReader_17
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_18
    <REJECTED> -> AttributeRenamer
AttributeExposer_18
    ATTR_LIST = td_id,rk_dep,rk_extid,rk_xyfel
    -> Tester_9
Tester_9
    BOOL_OP = OR
    TEST_CLAUSE = TEST rk_extid ATTRIBUTE_HAS_A_VALUE ""
    TEST_MODE = TEST
    PASSED -> FeatureMerger_9 [SUPPLIER]
FeatureReader_18
    ATTR_ACCUM_MODE = Only Use Result
    COMBINE_GEOM = Use Result
    DATASET = @Value(Dataset)
    FEATURETYPES = @Value(fme_feature_type_name)
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = @Value(Dataset)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    <OTHER> -> AttributeExposer_10
    <REJECTED> -> AttributeRenamer
AttributeExposer_10
    ATTR_LIST = obj_id
    -> FeatureMerger_9 [REQUESTOR]
FeatureMerger_9
    ATTR_ACCUM_MODE = Merge Supplier
    ATTR_CONFLICT_RES = Use Requestor
    IGNORE_NULLS = No
    JOIN_KEYS = @Value(obj_id) @Value(td_id) AUTO
    MERGE_TYPE = Attributes Only
    PROCESS_DUPS = NO
    REJECT_NULL_MISSING_KEYS = No
    SUPPLIERS_FIRST = No
    MERGED -> Output (output)
    <REJECTED> -> AttributeRenamer
Output (output)
AttributeRenamer
    ATTR_TABLE:
      RENAME_SET_DEFAULT _reader_error > error_msg
      RENAME_SET_DEFAULT fme_rejection_code > error_msg
    -> <Rejected> (output)
<Rejected> (output)

Bookmark: rk_fastighet_l
Input (input)
    -> FeatureReader [INITIATOR]
Input_2 (input)
    -> FeatureReader_2 [INITIATOR]

Bookmark: rk_fastighet_p
Input_3 (input)
    -> FeatureReader_3 [INITIATOR]
Input_4 (input)
    -> FeatureReader_4 [INITIATOR]

Bookmark: rk_fastighet_y
Input_5 (input)
    -> FeatureReader_5 [INITIATOR]
Input_6 (input)
    -> FeatureReader_6 [INITIATOR]

Bookmark: rk_fastighetadmtext_p
Input_7 (input)
    -> FeatureReader_7 [INITIATOR]
Input_8 (input)
    -> FeatureReader_8 [INITIATOR]

Bookmark: rk_fastighetgrans_l
Input_9 (input)
    -> FeatureReader_9 [INITIATOR]
Input_10 (input)
    -> FeatureReader_10 [INITIATOR]

Bookmark: rk_fastighetid_p
Input_11 (input)
    -> FeatureReader_11 [INITIATOR]
Input_12 (input)
    -> FeatureReader_12 [INITIATOR]

Bookmark: rk_fastighetidtext_p
Input_13 (input)
    -> FeatureReader_13 [INITIATOR]
Input_14 (input)
    -> FeatureReader_14 [INITIATOR]

Bookmark: rk_fastighettext_p
Input_15 (input)
    -> FeatureReader_15 [INITIATOR]
Input_16 (input)
    -> FeatureReader_16 [INITIATOR]

Bookmark: rk_granspunkt_p
Input_17 (input)
    -> FeatureReader_17 [INITIATOR]
Input_18 (input)
    -> FeatureReader_18 [INITIATOR]
