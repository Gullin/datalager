FME workspace raa-DatalagerManage-main.fmw

Parameters:
- DestDataset_POSTGIS =
- DestDataset_POSTGIS_14 =
- FME_USER_PARAM_PRIVATE_GRP =
- InData =
- InData-DatabaseTable =
- IsWholeProcessRun =
- Klippytor =
- Manifest =
- OutSchemaFileNameSuffix =
- OutputDirectory =
- PG_SCHEMA =
- ProcessModulName =
- ProcessName =
- RotDirectory =
- SchemaFlush =

Readers:
- FFS_1: FFS from $(Klippytor)
- OGCGEOPACKAGE_1: OGCGEOPACKAGE from $(InData)
- XLSXR_1: XLSXR from $(Manifest)

Writers:
- SDF3_1: SDF3 to $(OutputDirectory) in EPSG:3008
- SHAPEFILE_1: SHAPEFILE to $(OutputDirectory) in EPSG:3008
- POSTGIS_1: POSTGIS to $(DestDataset_POSTGIS) in EPSG:3008
- POSTGIS_2: POSTGIS to $(DestDataset_POSTGIS_14) in EPSG:3008

Note: Workspace som inte används direkt, utan kallas på genom ett s.k. driver-workspace / Parametrar / Parametrarna sätts i DRIVER-skriptet programmatiskt / * [RotDirectory] Kommer från batch-processen och är obligatoriskt för alla FME-processor. / * [ProcessName] Kommer från batch-processen och är obligatoriskt för alla FME-processor. / * [Manifest] Excel-fil från ett tidigare exporterat schema anpassad med nya kolumnnamn samt vilken data som ska exporteras. Används i detta skript för att bygga upp gällande schema för resp. feature type. / * [OutputDirectory] Katalogsökväg för exporterad geodata (delrepository). / * [ProcessModulName] / * [IsWholeProcesRun]
KlippytorSweref99TM1330 (reader FFS_1)
    attributes: Projektion varchar(200), Namn varchar(200)
    -> TestFilter
TestFilter
    DEFAULT_VALUE = <UNFILTERED>
    TEST_LIST:
      BOOL_OP,AND,COMPOSITE_TEST,<Unused>,TEST_CLAUSE,"TEST @Value(Namn) = Landskrona
      TEST @Value(Projektion) = SW99TM",Landskrona-SW99TM
    Landskrona-SW99TM -> Bufferer
Note: Klipper totalt 1,5 km utanför kommungräns. / Buffrar med 1445 m eftersom standardklippytan / är 5 m utanför kommungräns.
Bufferer
    ANGLE = 22.5
    CAP_STYLE = Arc
    CORNER_STYLE = Arc
    MODE = AREA
    OFFSET = 1445
    OFFSET_UNITS = NONE
    PRECISION = APPROX
    BUFFERED -> Clipper [CLIPPER]
Skåne_län_Shape_Net_VAG (reader OGCGEOPACKAGE_1)
    attributes: RLID text(38), FRAN_DATUM mediumint, TILL_DATUM mediumint, STARTAVST double, SLUTAVST double, AADAXEPAAR mediumint, AADLASBIAR mediumint, AADTFORDON mediumint, AALERSLASS mediumint, AARTA8 mediumint, AARTAL mediumint, AARTAL1 mediumint, AARTAL2 mediumint, AATAERAAAA smallint, AATAERANEN smallint, AATAERANRD smallint, AATAERARND smallint, AATAERBAEL smallint, AATAERBAOR smallint, AATAERBOET smallint, AATAERBUDD smallint, AATAERBYG2 smallint, AATAERBYON smallint, AATAERFLGA smallint, AATAERFOND smallint, AATAERHYAE smallint, AATAERHYGT smallint, AATAERHYNG smallint, AATAERLEOR smallint, AATAERMATS smallint,
      AATAEROEGT smallint, AATAERRIEG smallint, AATAERRING smallint, AATAERSAMA smallint, AATAERSDUM date, AATAERSINT smallint, AATAERSTDD smallint, AATAERSTEL smallint, AATAERTACK smallint, AATAERTIER smallint, AATAERTIRO smallint, AATAERTOMA smallint, AATAERTRAN smallint, AATAERTRNG smallint, AATAERTRUM smallint, AATAERVAAR smallint, AATGERBYG1 smallint, ABSORBENT text(254), AEGARE text(254), AGARE text(3000), AHOTADE smallint, ALIASNAME text(200), ALLÉTYP text(254), ALTRNAIV15 double, ALTRNAIVAT double, ALTRNAIVNG text(50), ANDLRAFFAT mediumint, ANLEGGINER text(3000), ANSVARORG mediumint, ANTAL mediumint,
      ANTALSPAAR mediumint, ANTLMAKE21 mediumint, ANTLMAKEIL mediumint, ANTLTRMMOR mediumint, ATGAERSDUM date, ATK_ID text(3000), ATTRIBUTE text, AVFRTSAEEG text(254), AVKERNNG13 double, AVKERNNGAT double, AVSITTIDET mediumint, AVST double, AVVKANEUAR text(254), BAEIGHTSOD text(254), BAEIGHTSSS text(254), BESKRGFART text(3000), BESKRPV text(500), BETECKNING text(50), BEVVARD text(3000), BIOOGIKTDE text(254), BORMEDITER text(254), BREDD double, BROANDKAAP mediumint, BROCHTNNEL text(254), BROYTA double, BRUTTOVIKT double, BSALLSNTTA smallint, BSEKR_GEJ1 text(3000), BUSSGATA text(254), BYGGAAR mediumint,
      CHAVDGNNDE smallint, CIRULAIOTS text(254), CODE text, DAGSL1 text(254), DAGSL11 text(254), DAGSL12 text(50), DAGSL2 text(254), DAGSL21 text(254), DAGSL3 text(254), DAGSL31 text(254), DAGSLAG mediumint, DIM1 mediumint, DIMENS_AR mediumint, DRIBLOMADE smallint, DRIFTKLASS text(254), DRIFTSTART date, EBERAESAEN smallint, ENKLDUBEIG text(254), ENTEPRNOER mediumint, ESTTISTVDE text(254), EUROPAVÄG smallint, EXPNERARET mediumint, E_KORDNAAT mediumint, FARINTE text(254), FIELDNAME text(200), FLYGHJD1 mediumint, FNYKELTRER smallint, FOEBINELRI text(254), FOEVALARRE text(254), FOEVALNIRM text(254),
      FORDTRA11 text(254), FORDTRA110 text(254), FORDTRA12 text(254), FORDTRA13 text(254), FORDTRA14 text(254), FORDTRA15 text(254), FORDTRA16 text(254), FORDTRA17 text(254), FORDTRA18 text(254), FORDTRA19 text(254), FORDTRAF1 text(254), FORDTRAF11 text(254), FORDTRAF12 text(254), FORDTRAF13 text(254), FORDTRAF2 text(254), FORDTRAF3 text(254), FORDTYP1 text(254), FORDTYP11 mediumint, FORDTYP12 mediumint, FORDTYP13 mediumint, FORDTYP2 text(254), FORDTYP3 text(254), FORDTYP4 text(254), FORDTYP5 text(254), FORD_BREDD double, FORD_LGD double, FORD_TAG text(254), FORVALTARE text(3000), FOTO1 text(512), FOTO2 text(512),
      FOTO3 text(512), FO_OBJ_ID text(12), FPVKLASS mediumint, FRANRLFRAV double, FRANRLTIAV double, FRIHOJD double, FUNDAMENT text(254), FUNKTYP text(3000), GAAGATA text(254), GAAGFATSDE text(254), GAETVAG113 text(10), GAETVAG1EG text(254), GAETVAG1ER text(10), GAETVAG216 text(10), GAETVAG2EG text(254), GAETVAG2ER text(10), GATUNAMN text, GCMTYP text(254), GEDAGSL11 text(254), GEDAGSL12 text(254), GENMGAENEG text(254), GENOMFART text(254), GENRALSEYP text(254), GESLDAG11 text(254), GESLDAG12 text(254), GESLDAT11 date, GESLDAT12 date, GESLMIN111 mediumint, GESLMIN112 mediumint, GESLMIN121 mediumint,
      GESLMIN122 mediumint, GESLTIM111 mediumint, GESLTIM112 mediumint, GESLTIM121 mediumint, GESLTIM122 mediumint, GESTDAG11 text(254), GESTDAG12 text(254), GESTDAT11 date, GESTDAT12 date, GESTMIN111 mediumint, GESTMIN112 mediumint, GESTMIN121 mediumint, GESTMIN122 mediumint, GESTTIM111 mediumint, GESTTIM112 mediumint, GESTTIM121 mediumint, GESTTIM122 mediumint, GODAENANUM date, GRUDLAGGYP text(254), GUTECKINRK smallint, HAALPLTSID mediumint, HAALPLTSMN text(100), HAALPLTSYP text(254), HARKOESEAN smallint, HAVGIE1 mediumint, HAVHAST1 mediumint, HINDER mediumint, HINDERTYP text(254), HOEJD double, HOJDID text(3000),
      HTHAST mediumint, HUVDKOSTYP text(254), HUVUDNR mediumint, IDENTITET text(3000), INDSTRVAEG text(254), INFRSTRDEL text(254), JVGBANDEL text(3), JVGILOETER mediumint, JVGMETER mediumint, KAMENR text(12), KANTREMSA text(254), KATEGORI text(254), KFBESKRIVN text(254), KLASIFCENG text(254), KLASS text(254), KLASSATT text(3000), KLASSNING text(254), KOEFAETIN1 text(200), KOEFAETING text(200), KOEFAETKNA text(254), KOEFAETSAL mediumint, KOEFAETSNS text(200), KOMMUNKOD text, KOMMUNNAMN text(38), KOMPROC1 text(3000), KONAKTEDNG mediumint, KONROLMAUM mediumint, KONSTHUTYP text(3000), KONSTLANGD double, KONSTNAMN text(3000),
      KONSTNR text(3000), KONSTRYTA double, KONTRUTIER text(3000), KONTRUTION text(254), KORMAGSIIN text(254), KULURHSTDE text(254), KVAITESSAD text(254), LAEGE mediumint, LAENGD mediumint, LAENINSTYP text(254), LAENSBET text, LAENSKOD text, LAENSNAMN text, LANKROLL mediumint, LATINTEMNG text(254), LEDSNAMN text(3000), LEDSTRAAK text(254), LEDUVUMAAN text(3000), LEKTRUTNNG text(254), LOEPNUMME1 mediumint, LOEPNUMME2 mediumint, LOEPNUMME9 mediumint, LOEPNUMMER mediumint, LÄN mediumint, MAEAARPEOD mediumint, MAETMETOD mediumint, MATERIAL text(254), MATRIATYYP text(254), MEDELFEL1 double, MEDETEARCK mediumint,
      METREFLIN1 mediumint, MILOEZNKSS text(254), MIN13 mediumint, MINUT mediumint, MOLOK text(254), MOTVERNGNG text(3000), NAMN text(3000), NEDONTRAAD date, NR mediumint, NYBY_OBJID text(12), NYGBYGGAR mediumint, NY_BYGG_AR mediumint, N_KORDNAAT mediumint, NÄTTYP mediumint, OBJEKTID text(3000), OEPNINSALA mediumint, OEPNINSBAR text(254), OEVIGURUNG text(500), ORDNINGSNR mediumint, ORGANISAT text(254), ORGNISTI1 mediumint, ORGNISTI2 mediumint, ORGNISTIER text(11), ORGNISTIO7 mediumint, ORGNISTIOD mediumint, ORT text(30), OSAKERETA3 mediumint, OSAKERETAR mediumint, OSAKERETON mediumint, PAABRO text(254),
      PASAGEAEGD double, PASAGEOEJD double, PASAGEREDD double, PASSAGETYP text(254), PASSBREDD double, PIOJAEKOON mediumint, PIOJAEMAAL mediumint, PLACERING text(254), PLAKORNIID text(20), PLATFOMSDD double, PLATFOMSGD double, PLATFOMSJD mediumint, PLATS1 text(255), PLATTFORM text(254), PORALHEJJD double, PRIMANV mediumint, RAAENR text(3000), RAEFELREDD mediumint, RAEFFELTYP mediumint, RASPLASASS text(100), RASPLASNMN text(100), REFGPASAGE text(254), REGIONKOD mediumint, REGIONNAMN text(38), REKOMEND text(254), RESTAURANG text(254), RIKTNING text(254), RIKTNING2 text(254), RISK text(254), SAEERHTSDD text(500),
      SAELSYTHET mediumint, SENSTANDAD mediumint, SEPARATION mediumint, SEQ_NO mediumint, SERICEIVAA text(254), SIDA text(254), SIDAFT text(254), SIDAVSAAJE mediumint, SIDAVSAANT mediumint, SIDTYP text(254), SIGALRGLNG text(254), SKADOR text(254), SKALFKT1 mediumint, SKONHESVDE mediumint, SKOTSEANIG text(254), SKOTSEANNG text(254), SKOTSESTUS text(254), SLDAG1 text(254), SLDAG11 text(254), SLDAG12 text(50), SLDAG2 text(254), SLDAG21 text(254), SLDAG3 text(254), SLDAG31 text(254), SLDAT1 date, SLDAT11 date, SLDAT12 date, SLDAT2 date, SLDAT21 date, SLDAT3 date,
      SLDAT31 date, SLITLAG1 text(254), SLMIN11 mediumint, SLMIN111 mediumint, SLMIN112 mediumint, SLMIN12 mediumint, SLMIN121 mediumint, SLMIN122 mediumint, SLMIN21 mediumint, SLMIN211 mediumint, SLMIN212 mediumint, SLMIN22 mediumint, SLMIN31 mediumint, SLMIN311 mediumint, SLMIN312 mediumint, SLMIN32 mediumint, SLTIM11 mediumint, SLTIM111 mediumint, SLTIM112 mediumint, SLTIM12 mediumint, SLTIM121 mediumint, SLTIM122 mediumint, SLTIM21 mediumint, SLTIM211 mediumint, SLTIM212 mediumint, SLTIM22 mediumint, SLTIM31 mediumint, SLTIM311 mediumint, SLTIM312 mediumint, SLTIM32 mediumint,
      SLUDATMSOD date, SLUDATMVOD date, SLUTDAG mediumint, SLUTDAT1 date, SLUTDATUM date, SOPKAERL text(254), STARTDAG mediumint, STARTDATUM date, STATDAUMO3 date, STATDAUMOD date, STDAG1 text(254), STDAG11 text(254), STDAG12 text(50), STDAG2 text(254), STDAG21 text(254), STDAG3 text(254), STDAG31 text(254), STDAT1 date, STDAT11 date, STDAT12 date, STDAT2 date, STDAT21 date, STDAT3 date, STDAT31 date, STMIN11 mediumint, STMIN111 mediumint, STMIN112 mediumint, STMIN12 mediumint, STMIN121 mediumint, STMIN122 mediumint,
      STMIN21 mediumint, STMIN211 mediumint, STMIN212 mediumint, STMIN22 mediumint, STMIN31 mediumint, STMIN311 mediumint, STMIN312 mediumint, STMIN32 mediumint, STOLPTYP mediumint, STTIM11 mediumint, STTIM111 mediumint, STTIM112 mediumint, STTIM12 mediumint, STTIM121 mediumint, STTIM122 mediumint, STTIM21 mediumint, STTIM211 mediumint, STTIM212 mediumint, STTIM22 mediumint, STTIM31 mediumint, STTIM311 mediumint, STTIM312 mediumint, STTIM32 mediumint, SVANGMEJSS mediumint, SVFRANR mediumint, SVFRANRL text(38), SVNOD text(38), SVTILLR mediumint, SVTILLRL text(38), TAAGFLOEDE mediumint,
      TENLAEKIID mediumint, TENLAEKNMN text(40), TENLOGSKID mediumint, TILGAEGLET mediumint, TILLAXLAST double, TILLBOLAST double, TILLRLFRAV double, TILLRLTIAV double, TIM12 mediumint, TIMME mediumint, TOALETT text(254), TOTALVIKT double, TOTALVIKT1 double, TOTLTATAED mediumint, TOTLVARDNG mediumint, TPLUNDRNER text(2), TRADNUMEER mediumint, TRADSLG10A mediumint, TRADSLG110 text(254), TRADSLG1AL mediumint, TRADSLG2AL mediumint, TRADSLG3AL mediumint, TRADSLG4AL mediumint, TRADSLG5AL mediumint, TRADSLG6AL mediumint, TRADSLG7AL mediumint, TRADSLG8AL mediumint, TRADSLG9AL mediumint, TRAEDSLAG text(254), TRAEDSLAG1 text(254),
      TRAEDSLAG2 text(254), TRAEDSLAG3 text(254), TRAEDSLAG4 text(254), TRAEDSLAG5 text(254), TRAEDSLAG6 text(254), TRAEDSLAG7 text(254), TRAEDSLAG8 text(254), TRAEDSLAG9 text(254), TRAFIKKL1 text(254), TRAIKATEON mediumint, TRAIKATTYP text(254), TRAIKPATER mediumint, TRYCK1 double, TRYCK2 double, TRYCK3 double, TYP mediumint, TYPFORDON text(3000), TYPTRYCK1 text(254), TYPTRYCK2 text(254), TYPTRYCK3 text(254), UHTYPVAG text(254), UNDERNR mediumint, UPPAMLNDDE text(254), UPPEVESEDE mediumint, UPPTAELBGD mediumint, URSRUNLIET mediumint, UTPKADAETS text(254), UTSRAEKNNG text(254), VAEDEKASSS text(254), VAEDVAGEEG text(254),
      VAEDVAGHER text(10), VAEDVAGUER text(10), VAEERSYDDD text(254), VAEGSKYDD mediumint, VAEHAALAMN text(3000), VAEHAALAYP text(254), VAENAEFOER text(254), VAEPROILEN mediumint, VAEPROILNG mediumint, VAEPROILVA mediumint, VAETRAIKYP text(254), VAGBABREDD double, VAGDELSN1 mediumint, VAGNR1 mediumint, VALUE text, VARDVAG mediumint, VERKSAMH11 text(254), VERKSAMH12 text(254), VERKSAMH13 text(254), VERKSAMH14 text(254), VERKSAMH15 text(254), VERKSAMH16 text(254), VERKSAMH17 text(254), VIKIGATEAG text(3000), VILPASAGAR mediumint, VILUTHPPAR mediumint, VINERETRER mediumint, VINKEL mediumint, VITALITET text(254), XKOORD double,
      XKOORDINAT double, XKORDIATRT mediumint, XKORDIATUT mediumint, YKOORD double, YKOORDINAT double, YKORDIATRT mediumint, YKORDIATUT mediumint, ZKOORD double
    -> ParameterFetcher
ParameterFetcher
    ATTR_LIST = ProcessName $(ProcessName) RotDirectory $(RotDirectory)
    -> StringConcatenator
StringConcatenator
    ACTION = Create New Attribute
    PARM_LINE = @Value(ProcessName)_MAIN
    VAL_ATTR = ProcessName_MAIN
    -> UUIDGenerator
UUIDGenerator
    UUID_ATTR = ProcessID
    -> Clipper [CLIPPEE]
    -> Sampler_2
Clipper
    BOUNDARY_CASES = Treat as Inside
    CLEANING_TOLERANCE = None
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> SchemaMapper
    <REJECTED> -> Aggregator_5
SchemaMapper
    DATASET = $(Manifest)
    FORMAT = XLSXR
    IDXDESTATTR = fme_feature_type
    IDXDESTCOL = ""
    IDXSOURCEATTR = fme_feature_type
    IDXSOURCECOL = ""
    MAP_ATTRS = column_name dl_new_column_name $(FME_ASC_16)
    ROW_ID_ATTR = _schemamapper_row_ids
    TABLE = schema
    XLSXR_ALLOW_DOLLAR_SIGNS = YES
    XLSXR_CASE_SENSITIVE_FEATURE_TYPES = YES
    XLSXR_CONFIGURATION_DATASET = $(Manifest)
    XLSXR_CREATE_FEATURE_TABLES_FROM_DATA = Yes
    XLSXR_EXCEL_COL_NAMES = YES
    XLSXR_EXPAND_MERGED_CELLS = Yes
    XLSXR_FORCE_DATETIME = NO
    XLSXR_KEEP_SCHEMA_SETTINGS = YES
    XLSXR_QUERY_FEATURE_TYPES_FOR_MERGE_FILTERS = Yes
    XLSXR_READ_BLANK_AS = Missing
    XLSXR_READ_RASTER_MODE = None
    XLSXR_SCAN_SCHEMA_IF_DYNAMIC = No
    XLSXR_SCHEMA = schema,0,filter_fme_feature_type,char,17,,,1,filter_export_column,char,10,,,2,fme_feature_type_name,char,26,,,3,column_name,char,11,,,4,dl_need_new_column_name,char,6,,,5,dl_new_column_name,char,11,,,6,dl_export,char,5,,,7,fme_data_type,char,20,,,8,native_data_type,char,15,,,9,fme_format_long_name,char,15,,,10,fme_format_short_name,char,10,,,11,_dirpath,char,80,,,12,_extension,char,4,,,13,DatasetFull,char,30,,,14,Dataset,char,26,,,15,column_name_char_length,number,3," 0",,1,,,,NO,NO,1,$(Manifest),"0,0,15,1714",,NO,NO
    XLSXR_STRIP_SHEETNAME_SPACES = YES
    XLSXR_TABLELIST = schema
    XLSXR_TRIM_ATTR_NAME_WHITESPACE = Yes
    XLSXR_USE_SCHEMA_OTHER_FILES = No
    MAPPED -> FeatureMerger [REQUESTOR]
    UNMAPPED -> Aggregator_6
schema (reader XLSXR_1)
    attributes: filter_fme_feature_type char(17), filter_export_column char(10), fme_feature_type_name char(60), column_name char(11), dl_need_new_column_name char(6), dl_new_column_name char(11), dl_export char(6), fme_data_type char(18), native_data_type char(11), fme_format_long_name char(15), fme_format_short_name char(14), _dirpath char(70), _extension char(5), DatasetFull char(15), Dataset char(10), column_name_char_length number(3,0)
    -> Tester
Tester
    BOOL_OP = OR
    COMPOSITE_TEST = 1
    TEST_CLAUSE = TEST @Value(dl_export) = true
    TEST_MODE = TEST
    PASSED -> AttributeManager
AttributeManager
    ATTR_TABLE:
      REMOVE filter_fme_feature_type
      REMOVE filter_export_column
      REMOVE column_name
      REMOVE dl_need_new_column_name
      RENAME_SET_VALUE dl_new_column_name > name
      REMOVE dl_export
      REMOVE _dirpath
      REMOVE _extension
      REMOVE DatasetFull
      REMOVE Dataset
      REMOVE column_name_char_length
    -> Aggregator_2
Aggregator_2
    ACCUM_ATTRS_NAME = Use Attributes From One Feature
    AGGREGATE_TYPE = Homogeneous Collection (If Possible)
    COUNT_ATTR = Antal
    GROUP_BY = fme_feature_type fme_feature_type_name fme_format_long_name fme_format_short_name
    LIST_ATTRS_TO_INCLUDE = fme_data_type name native_data_type
    LIST_NAME = attribute
    MODE = Geometry - Assemble One Level
    SEP = ,
    AGGREGATE -> AttributeKeeper_2
AttributeKeeper_2
    CREATE_BULK_MODE_FEATURES = NO
    KEEP_ATTRS = fme_feature_type_name,fme_format_long_name,fme_format_short_name
    KEEP_LIST = attribute{}
    -> FeatureMerger [SUPPLIER]
FeatureMerger
    ATTR_ACCUM_MODE = Merge Supplier
    ATTR_CONFLICT_RES = Use Requestor
    IGNORE_NULLS = No
    JOIN_KEYS = @Value(fme_feature_type) @Value(fme_feature_type_name) AUTO
    MERGE_TYPE = Attributes Only
    PROCESS_DUPS = NO
    REJECT_NULL_MISSING_KEYS = No
    SUPPLIERS_FIRST = No
    MERGED -> GtransReprojector
    UNMERGED_REQUESTOR -> Aggregator_8
GtransReprojector
    INTERPOLATION_TYPE_NAME = Nearest Neighbor
    RASTER_CELL_SIZE = Square Cells
    RASTER_TOLERANCE = 0.0
    TRANSLATION_FILE = $(FME_HOME)Reproject\Gtrans\Sys\SW99TM-1330.tf
    REPROJECTED -> AttributeCreator
AttributeCreator
    ATTR_TABLE = SET_TO _name_extension
    -> ArcStroker
Note: ArcStroker [ArcStroker] / General: / Stroke By: Maximum Deviation / Maximum Deviation: 0.02 / Make Polygon Out of 360 Degree Arcs: No
ArcStroker
    MAKE_POLY = No
    STROKE_CHOICE = Maximum Deviation
    TOLERANCE_VAL = 0.02
    STROKED -> 2DForcer
2DForcer
    2D -> GeometryRefiner
GeometryRefiner
    -> GeometryFilter
GeometryFilter
    BREAK_AGG = No
    GEOM_PORT_NAMES = Point Line Arc Area Ellipse Text Raster "Point Cloud" Surface Solid Collection Null Instance
    POINT -> StringConcatenator_4
    LINE -> StringConcatenator_5
    ARC -> StringConcatenator_31
    AREA -> StringConcatenator_6
    ELLIPSE -> StringConcatenator_32
    TEXT -> StringConcatenator_7
    RASTER -> Junction_6
    POINTCLOUD -> Junction_6
    SURFACE -> Junction_6
    SOLID -> Junction_6
    COLLECTION -> Junction_6
    NULL -> Junction_6
    INSTANCE -> Junction_6
    <UNFILTERED> -> Junction_6
StringConcatenator_4
    ACTION = Create New Attribute
    PARM_LINE = @Value(fme_feature_type)@Value(_name_extension)_p
    VAL_ATTR = DatasetName
    -> StringCaseChanger_5
StringConcatenator_5
    ACTION = Create New Attribute
    PARM_LINE = @Value(fme_feature_type)@Value(_name_extension)_l
    VAL_ATTR = DatasetName
    -> StringCaseChanger_2
StringConcatenator_31
    ACTION = Create New Attribute
    PARM_LINE = @Value(fme_feature_type)@Value(_name_extension)_l
    VAL_ATTR = DatasetName
    -> StringCaseChanger_3
StringConcatenator_6
    ACTION = Create New Attribute
    PARM_LINE = @Value(fme_feature_type)@Value(_name_extension)_y
    VAL_ATTR = DatasetName
    -> StringCaseChanger_4
StringConcatenator_32
    ACTION = Create New Attribute
    PARM_LINE = @Value(fme_feature_type)@Value(_name_extension)_y
    VAL_ATTR = DatasetName
    -> StringCaseChanger_6
StringConcatenator_7
    ACTION = Create New Attribute
    PARM_LINE = @Value(fme_feature_type)@Value(_name_extension)_t
    VAL_ATTR = DatasetName
    -> StringCaseChanger_5
Junction
    -> schema (writer POSTGIS_1)
    -> Table1 (writer POSTGIS_2)
    -> Shapefile1 (writer SHAPEFILE_1)
Note: : [SHAPEFILE]
Shapefile1 (writer SHAPEFILE_1)
Junction_6
    -> Aggregator
Creator
    GEOMTYPE = Geometry Object
    NUM = 1
    CREATED -> ParameterFetcher_2
ParameterFetcher_2
    ATTR_LIST = ProcessName $(ProcessName) RotDirectory $(RotDirectory)
    -> StringConcatenator_8
StringConcatenator_8
    ACTION = Create New Attribute
    PARM_LINE = @Value(ProcessName)_MAIN
    VAL_ATTR = ProcessName_MAIN
    -> UUIDGenerator_2
UUIDGenerator_2
    UUID_ATTR = ProcessID
    -> AttributeCreator_12_OUTPUT
AttributeCreator_12_OUTPUT: Junction
    -> FeatureMerger_2 [SUPPLIER]
    -> FeatureMerger_3 [SUPPLIER]
    -> FeatureMerger_4 [SUPPLIER]
    -> FeatureMerger_5 [SUPPLIER]
    -> FeatureMerger_6 [SUPPLIER]
    -> FeatureMerger_7 [SUPPLIER]

Bookmark: Loggning
Aggregator_6
    ACCUM_ATTRS_NAME = Use Attributes From One Feature
    AGGREGATE_TYPE = Homogeneous Collection (If Possible)
    GROUP_BY = fme_feature_type
    MODE = Geometry - Assemble One Level
    SEP = ", "
    AGGREGATE -> Aggregator_7
Aggregator_7
    ACCUM_ATTRS_NAME = Use Attributes From One Feature
    AGGREGATE_TYPE = Homogeneous Collection (If Possible)
    CONCAT_ATTRS = fme_feature_type
    MODE = Geometry - Assemble One Level
    SEP = ", "
    AGGREGATE -> FeatureMerger_6 [REQUESTOR]
Aggregator_5
    ACCUM_ATTRS_NAME = Use Attributes From One Feature
    AGGREGATE_TYPE = Homogeneous Collection (If Possible)
    COUNT_ATTR = Antal
    MODE = Geometry - Assemble One Level
    SEP = ", "
    AGGREGATE -> FeatureMerger_5 [REQUESTOR]
Note: Endast till för som signal att starta logg
Sampler_2
    RATE = 1
    SAMPLE_MODE = No
    SAMPLE_TYPE_LONG = First N Features
    SAMPLED -> FeatureMerger_2 [REQUESTOR]
Junction_2
    -> Aggregator_4
Aggregator_4
    ACCUM_ATTRS_NAME = Use Attributes From One Feature
    AGGREGATE_TYPE = Homogeneous Collection (If Possible)
    COUNT_ATTR = Antal
    MODE = Geometry - Assemble One Level
    SEP = ", "
    AGGREGATE -> FeatureMerger_4 [REQUESTOR]
Aggregator
    ACCUM_ATTRS_NAME = Use Attributes From One Feature
    AGGREGATE_TYPE = Homogeneous Collection (If Possible)
    GROUP_BY = fme_feature_type
    MODE = Geometry - Assemble One Level
    SEP = ,
    AGGREGATE -> Aggregator_3
Aggregator_3
    ACCUM_ATTRS_NAME = Use Attributes From One Feature
    AGGREGATE_TYPE = Homogeneous Collection (If Possible)
    CONCAT_ATTRS = fme_feature_type
    COUNT_ATTR = Antal
    MODE = Geometry - Assemble One Level
    SEP = ", "
    AGGREGATE -> FeatureMerger_3 [REQUESTOR]
Aggregator_8
    ACCUM_ATTRS_NAME = Use Attributes From One Feature
    AGGREGATE_TYPE = Homogeneous Collection (If Possible)
    GROUP_BY = fme_feature_type
    MODE = Geometry - Assemble One Level
    SEP = ", "
    AGGREGATE -> Aggregator_9
Aggregator_9
    ACCUM_ATTRS_NAME = Use Attributes From One Feature
    AGGREGATE_TYPE = Homogeneous Collection (If Possible)
    CONCAT_ATTRS = fme_feature_type
    MODE = Geometry - Assemble One Level
    SEP = ", "
    AGGREGATE -> FeatureMerger_7 [REQUESTOR]
FeatureMerger_5
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_10
StringConcatenator_10
    ACTION = Create New Attribute
    PARM_LINE = @Value(Antal)st. objekt avslogs att klippas med transformern Clipper.
    VAL_ATTR = Logg
    -> DTStamperYYYY-MM-DD_HH:MI:SS.sss_2
DTStamperYYYY-MM-DD_HH:MI:SS.sss_2
    -> Logg_5
Logg_5: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,VARNING,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_3
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_3
StringConcatenator_3
    ACTION = Create New Attribute
    PARM_LINE = Geometrier från objektklasser (@Value(fme_feature_type)) skrivs ej till shape-filer.
    VAL_ATTR = Logg
    -> DTStamperYYYY-MM-DD_HH:MI:SS.sss_3
DTStamperYYYY-MM-DD_HH:MI:SS.sss_3
    -> Logg_3
Logg_3: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,VARNING,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_9
StringConcatenator_9
    ACTION = Create New Attribute
    PARM_LINE = @Value(ProcessName_MAIN) avslutad med @Value(Antal) st. objekt skrivna till datalagret.
    VAL_ATTR = Logg
    -> DTStamperYYYY-MM-DD_HH:MI:SS.sss_4
DTStamperYYYY-MM-DD_HH:MI:SS.sss_4
    -> Logg_4
Logg_4: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,KLART,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_2
StringConcatenator_2
    ACTION = Create New Attribute
    PARM_LINE = Kör @Value(ProcessName_MAIN) för data i "$(Manifest)" till datalagret.
    VAL_ATTR = Logg
    -> DTStamperYYYY-MM-DD_HH:MI:SS.sss
DTStamperYYYY-MM-DD_HH:MI:SS.sss
    -> Logg_2
Logg_2: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,INFORMATION,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_6
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_11
StringConcatenator_11
    ACTION = Create New Attribute
    PARM_LINE = fme_basicstring:37%24%31:Kolumner och dess namn i dataset(en) @Value(fme_feature_type) har ej länkats till nytt namn.
    VAL_ATTR = Logg
    -> DTStamperYYYY-MM-DD_HH:MI:SS.sss_5
DTStamperYYYY-MM-DD_HH:MI:SS.sss_5
    -> Logg_6
Logg_6: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)
FeatureMerger_7
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> StringConcatenator_12
StringConcatenator_12
    ACTION = Create New Attribute
    PARM_LINE = fme_basicstring:12%24%180:Dataset(en) @Value(fme_feature_type) har ej länkats till något schema. Kommer ej att kunna skapas med attribut. Kontrollera anledningen till att dataset åkt igenom utan upptagning på korrekt sätt i schemahanteringen.
    VAL_ATTR = Logg
    -> DTStamperYYYY-MM-DD_HH:MI:SS.sss_6
DTStamperYYYY-MM-DD_HH:MI:SS.sss_6
    -> Logg_7
Logg_7: WorkspaceRunner
    BLOCKING = No
    MAX_TO_BATCH = 1
    WORKSPACE_FILE = C:\dev\Datalager_procsrc\_sys\_logg.fmw
    WORKSPACE_PARAMETERS = EX_DATE_TIME,@Value(_datetimestamp),EX_PROCESS_NAME,@Value(ProcessName_MAIN),EX_ID,@Value(ProcessID),EX_TYPE,ERROR,EX,@Value(Logg),EX_WorkSpace,$(FME_MF_DIR_USERTYPED)$(FME_MF_NAME),EX_ROT_DIRECTORY,@Value(RotDirectory),EX_PROCESS_MODUL_NAME,$(ProcessModulName),IsWholeProcessRun,$(IsWholeProcessRun)

Bookmark: FDO_Line
StringCaseChanger_2
    ATTRCHOICE = Selected Attributes
    ATTRLIST = DatasetName
    CHANGE_TYPE = lowercase
    -> StringPairReplacer_2
    -> Junction_2
StringPairReplacer_2
    CASE = no
    MAP = å a Å a ä a Ä a ö o Ö o
    SRC_ATTRS = DatasetName
    -> FeatureClass10000 (writer SDF3_1)
    -> Junction
Note: : lkr_gis [SDF3] Line
FeatureClass10000 (writer SDF3_1)

Bookmark: FDO_Arc
StringCaseChanger_3
    ATTRCHOICE = Selected Attributes
    ATTRLIST = DatasetName
    CHANGE_TYPE = lowercase
    -> StringPairReplacer_3
    -> Junction_2
StringPairReplacer_3
    CASE = no
    MAP = å a Å a ä a Ä a ö o Ö o
    SRC_ATTRS = DatasetName
    -> FeatureClass10001 (writer SDF3_1)
    -> Junction
Note: : lkr_gis [SDF3] Arc
FeatureClass10001 (writer SDF3_1)

Bookmark: FDO_Area
StringCaseChanger_4
    ATTRCHOICE = Selected Attributes
    ATTRLIST = DatasetName
    CHANGE_TYPE = lowercase
    -> StringPairReplacer_4
    -> Junction_2
StringPairReplacer_4
    CASE = no
    MAP = å a Å a ä a Ä a ö o Ö o
    SRC_ATTRS = DatasetName
    -> FeatureClass10002 (writer SDF3_1)
    -> Junction
Note: : lkr_gis [SDF3] Area
FeatureClass10002 (writer SDF3_1)

Bookmark: FDO_Ellipse
StringCaseChanger_6
    ATTRCHOICE = Selected Attributes
    ATTRLIST = DatasetName
    CHANGE_TYPE = lowercase
    -> StringPairReplacer_5
    -> Junction_2
StringPairReplacer_5
    CASE = no
    MAP = å a Å a ä a Ä a ö o Ö o
    SRC_ATTRS = DatasetName
    -> FeatureClass10003 (writer SDF3_1)
    -> Junction
Note: : lkr_gis [SDF3] Ellipse
FeatureClass10003 (writer SDF3_1)

Bookmark: FDO_Point
StringCaseChanger_5
    ATTRCHOICE = Selected Attributes
    ATTRLIST = DatasetName
    CHANGE_TYPE = lowercase
    -> StringPairReplacer
    -> Junction_2
StringPairReplacer
    CASE = no
    MAP = å a Å a ä a Ä a ö o Ö o
    SRC_ATTRS = DatasetName
    -> Junction
    -> FeatureClass100 (writer SDF3_1)
Note: : lkr_gis [SDF3] Point
FeatureClass100 (writer SDF3_1)

Bookmark: PostGIS
Note: BUGG (FME 2021.0): / "Table Qualifier" i writer fungerar inte med dynamisk skrivning. Värdet behöver konkatineras i "Table Name"
schema (writer POSTGIS_1)
Table1 (writer POSTGIS_2)

FME custom transformer DTStamperYYYY-MM-DD_HH:MI:SS.sss
DTStamperYYYY-MM-DD_HH:MI:SS.sss
Skapar en tidsstämpel i specifika formatet YYYY-MM-DD HH:MI:SS.sss där
YYYY, År med fyra siffror
MM,   Månad med två siffror
DD,   Dag med två siffror
HH,   24-timmar med två siffror
MI,   Minuter med två siffror
SS,   Sekunder med två siffror
sss,  Millisekunder med tre siffror
Output
Attributet _datetimestamp

Input (input)
    -> DateTimeStamper
DateTimeStamper
    DATETIME_ATTR = _dts
    INCLUDE_OFFSET = NO
    STAMP_TYPE = datetime
    TIMEZONE = local
    -> DateTimeConverter
DateTimeConverter
    DATETIME_ATTR = _dts
    OUT_FORMAT = %Y-%m-%d %H:%M:%S
    PASSTHROUGH = NO
    REPAIR_INPUT = NO
    -> AttributeCreator
    <REJECTED> -> <Rejected> (output)
AttributeCreator
    ATTR_TABLE = SET_TO _mils = @Value(_dts)
    -> StringReplacer
StringReplacer
    CASE = NO
    FIND_TEXT = \.\d*
    NO_MATCH = _FME_NO_OP_
    REGEXP = YES
    SRC_ATTRS = _dts
    -> StringReplacer_2
StringReplacer_2
    CASE = NO
    FIND_TEXT = .*\.
    NO_MATCH = _FME_NO_OP_
    REGEXP = YES
    SRC_ATTRS = _mils
    -> SubstringExtractor
SubstringExtractor
    END = 2
    RESULT_ATTR = _subMils
    SRC_STRING = @Value(_mils)
    START = 0
    -> StringConcatenator
StringConcatenator
    ACTION = Create New Attribute
    PARM_LINE = @Value(_dts).@Value(_subMils)
    VAL_ATTR = _datetimestamp
    -> AttributeRemover
AttributeRemover
    REMOVE_ATTRS = _mils,_dts,_subMils
    -> Output (output)
Output (output)
<Rejected> (output)
